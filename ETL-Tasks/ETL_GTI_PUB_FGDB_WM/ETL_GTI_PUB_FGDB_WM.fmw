FME workspace ETL_GTI_PUB_FGDB_WM.fmw

Parameters:
- pEnv = STG   # Select Database Environment
- pOutput = \\dotb6gistest1\share\ArcGIS\Output\GTI_PUB_WM_STG.gdb   # Output File GDB

Starter
    -> AttributeCreator
AttributeCreator
    ATTR_TABLE = SET_TO p_SdeCoon = FME_CONDITIONAL:DEFAULT_VALUE'\\dotb6gistest1\share\ArcGIS\Resources\Connections\fme@STG_SDE_GTI_PUB_WM_STG.sde'BOOL_OP;OR;COMPOSITE_TEST;1;TEST $(pEnv) = PRD'\\dotb6gistest1\share\ArcGIS\Resources\Connections\fme@PRD_SDE_GTI_PUB_WM.sde'FME_NUM_CONDITIONS2___
    -> FeatureReader [INITIATOR]
FeatureReader
    ATTRIBUTES = DBO.All_Routes,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_01,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_02,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_03,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_04,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_05,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_06,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_07,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_08,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_09,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.All_Routes_District_10,"OBJECTID,FROMDATE,TODATE,CO_CountyID,CO_SignSystem,CO_RouteNumber,CO_SubRoute,CO_SuppCode,CO_RouteDirection,CO_ExitNumber,CO_RampLetter,CO_ROUTEID,SurveyDirection,CO_RouteLabel,Shape.STLength()",DBO.Dominant_Routes,"OBJECTID,ROUTEID,BMP,EMP,CountyCode,District,Route,SignSystem,SubRoute,SuppCode,Label,ROUTE_STATUS,Shape.STLength()",DBO.Dominant_Routes_District_01,"OBJECTID,ROUTEID,BMP,EMP,CountyCode,District,Route,SignSystem,SubRoute,SuppCode,Label,ROUTE_STATUS,Shape.STLength()",DBO.Dominant_Routes_District_02,"OBJECTID,ROUTEID,BMP,EMP,CountyCode,District,Route,SignSystem,SubRoute,SuppCode,Label,ROUTE_STATUS,Shape.STLength()",DBO.Dominant_Routes_District_03,"OBJECTID,ROUTEID,BMP,EMP,CountyCode,District,Route,SignSystem,SubRoute,SuppCode,Label,ROUTE_STATUS,Shape.STLength()",DBO.Dominant_Routes_District_04,"OBJECTID,ROUTEID,BMP,EMP,CountyCode,District,Route,SignSystem,SubRoute,SuppCode,Label,ROUTE_STATUS,Shape.STLength()",DBO.Dominant_Routes_District_05,"OBJECTID,ROUTEID,BMP,EMP,CountyCode,District,Route,SignSystem,SubRoute,SuppCode,Label,ROUTE_STATUS,Shape.STLength()",DBO.Dominant_Routes_District_06,"OBJECTID,ROUTEID,BMP,EMP,CountyCode,District,Route,SignSystem,SubRoute,SuppCode,Label,ROUTE_STATUS,Shape.STLength()",DBO.Dominant_Routes_District_07,"OBJECTID,ROUTEID,BMP,EMP,CountyCode,District,Route,SignSystem,SubRoute,SuppCode,Label,ROUTE_STATUS,Shape.STLength()",DBO.Dominant_Routes_District_08,"OBJECTID,ROUTEID,BMP,EMP,CountyCode,District,Route,SignSystem,SubRoute,SuppCode,Label,ROUTE_STATUS,Shape.STLength()",DBO.Dominant_Routes_District_09,"OBJECTID,ROUTEID,BMP,EMP,CountyCode,District,Route,SignSystem,SubRoute,SuppCode,Label,ROUTE_STATUS,Shape.STLength()",DBO.Dominant_Routes_District_10,"OBJECTID,ROUTEID,BMP,EMP,CountyCode,District,Route,SignSystem,SubRoute,SuppCode,Label,ROUTE_STATUS,Shape.STLength()",DBO.FEDERAL_FUNCTIONAL_CLASS_ROUTES,"OBJECTID,ROUTE_ID,FROM_MEASURE,TO_MEASURE,Length,NAT_FUNCTIONAL_CLASS,Shape.STLength()",DBO.Lane_Info_RH,"OBJECTID,route_id,from_measure,to_measure,CO_CountyID,CO_SignSystem,CO_RouteNumber,CO_SubRoute,CO_SuppCode,CO_RouteDirection,CO_ExitNumber,CO_RampLetter,SurveyDirection,CO_RouteLabel,AADT,AADT_YEAR,PAVEMENT_WIDTH_FT,SURFACE_TYPE,Shape.STLength()",DBO.Sub_Routes,"OBJECTID,RouteId,BMP,EMP,Label,SubRoute,SignSystem,SuppCode,Route,CountyCode,District,Shape.STLength()",DBO.WV_FUNCTIONAL_CLASSIFICATION_ROUTES,"OBJECTID,ROUTE_ID,FROM_MEASURE,TO_MEASURE,Length,STATE_FUNCTIONAL_CLASS,Shape.STLength()",DBO.WV_NHS_Routes,"OBJECTID,ROUTE_ID,FROM_MEASURE,TO_MEASURE,Length,NHS,Shape.STLength()"
    ATTR_ACCUM_MODE = Only Use Result
    COMBINE_GEOM = Use Result
    FEATURETYPES = DBO.All_Routes DBO.All_Routes_District_01 DBO.All_Routes_District_02 DBO.All_Routes_District_03 DBO.All_Routes_District_04 DBO.All_Routes_District_05 DBO.All_Routes_District_06 DBO.All_Routes_District_07 DBO.All_Routes_District_08 DBO.All_Routes_District_09 DBO.All_Routes_District_10 DBO.Dominant_Routes DBO.Dominant_Routes_District_01 DBO.Dominant_Routes_District_02 DBO.Dominant_Routes_District_03 DBO.Dominant_Routes_District_04 DBO.Dominant_Routes_District_05 DBO.Dominant_Routes_District_06 DBO.Dominant_Routes_District_07 DBO.Dominant_Routes_District_08 DBO.Dominant_Routes_District_09 DBO.Dominant_Routes_District_10 DBO.FEDERAL_FUNCTIONAL_CLASS_ROUTES DBO.Lane_Info_RH DBO.Sub_Routes DBO.WV_FUNCTIONAL_CLASSIFICATION_ROUTES DBO.WV_NHS_Routes
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(p_SdeCoon)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION_TYPE = Version from SDE Connection
    INTERACT = NONE
    OUTPUT_FEATURES_DISPLAY = Schema and Data Features
    DBO.All_Routes -> FeatureWriter [DBO.All_Routes]
    DBO.All_Routes_District_01 -> FeatureWriter [DBO.All_Routes_District_01]
    DBO.All_Routes_District_02 -> FeatureWriter [DBO.All_Routes_District_02]
    DBO.All_Routes_District_03 -> FeatureWriter [DBO.All_Routes_District_03]
    DBO.All_Routes_District_04 -> FeatureWriter [DBO.All_Routes_District_04]
    DBO.All_Routes_District_05 -> FeatureWriter [DBO.All_Routes_District_05]
    DBO.All_Routes_District_06 -> FeatureWriter [DBO.All_Routes_District_06]
    DBO.All_Routes_District_07 -> FeatureWriter [DBO.All_Routes_District_07]
    DBO.All_Routes_District_08 -> FeatureWriter [DBO.All_Routes_District_08]
    DBO.All_Routes_District_09 -> FeatureWriter [DBO.All_Routes_District_09]
    DBO.All_Routes_District_10 -> FeatureWriter [DBO.All_Routes_District_10]
    DBO.Dominant_Routes -> FeatureWriter [DBO.Dominant_Routes]
    DBO.Dominant_Routes_District_01 -> FeatureWriter [DBO.Dominant_Routes_District_01]
    DBO.Dominant_Routes_District_02 -> FeatureWriter [DBO.Dominant_Routes_District_02]
    DBO.Dominant_Routes_District_03 -> FeatureWriter [DBO.Dominant_Routes_District_03]
    DBO.Dominant_Routes_District_04 -> FeatureWriter [DBO.Dominant_Routes_District_04]
    DBO.Dominant_Routes_District_05 -> FeatureWriter [DBO.Dominant_Routes_District_05]
    DBO.Dominant_Routes_District_06 -> FeatureWriter [DBO.Dominant_Routes_District_06]
    DBO.Dominant_Routes_District_07 -> FeatureWriter [DBO.Dominant_Routes_District_07]
    DBO.Dominant_Routes_District_08 -> FeatureWriter [DBO.Dominant_Routes_District_08]
    DBO.Dominant_Routes_District_09 -> FeatureWriter [DBO.Dominant_Routes_District_09]
    DBO.Dominant_Routes_District_10 -> FeatureWriter [DBO.Dominant_Routes_District_10]
    DBO.FEDERAL_FUNCTIONAL_CLASS_ROUTES -> FeatureWriter [DBO.FEDERAL_FUNCTIONAL_CLASS_ROUTES]
    DBO.Lane_Info_RH -> FeatureWriter [DBO.Lane_Info_RH]
    DBO.Sub_Routes -> FeatureWriter [DBO.Sub_Routes]
    DBO.WV_FUNCTIONAL_CLASSIFICATION_ROUTES -> FeatureWriter [DBO.WV_FUNCTIONAL_CLASSIFICATION_ROUTES]
    DBO.WV_NHS_Routes -> FeatureWriter [DBO.WV_NHS_Routes]
FeatureWriter
    DATASET = $(pOutput)
    DATASET_ATTR = _dataset
    FEATURE_TYPE_LIST_ATTR = _feature_types
    FORMAT = GEODATABASE_FILE
    GEODATABASE_FILE_ANNOTATION_UNITS = unknown_units
    GEODATABASE_FILE_COMPRESS_AT_END = no
    GEODATABASE_FILE_COORDINATE_SYSTEM_GRANULARITY = FEATURE_TYPE
    GEODATABASE_FILE_DEFAULT_Z_VALUE = 0
    GEODATABASE_FILE_DESTINATION_DATASETTYPE_VALIDATION = Yes
    GEODATABASE_FILE_DUMP_FAILED_FEATURES = no
    GEODATABASE_FILE_ENABLE_FAST_DELETES = yes
    GEODATABASE_FILE_ENABLE_LOAD_ONLY_MODE = no
    GEODATABASE_FILE_GRID_1 = 0
    GEODATABASE_FILE_HAS_MEASURES = no
    GEODATABASE_FILE_HAS_Z_VALUES = auto_detect
    GEODATABASE_FILE_IGNORE_FAILED_FEATURE_ENTRY = no
    GEODATABASE_FILE_MAX_NUMBER_FAILED_FEATURES = -1
    GEODATABASE_FILE_OVERWRITE_GEODB = NO
    GEODATABASE_FILE_REQUESTED_GEODATABASE_VERSION = CURRENT
    GEODATABASE_FILE_SIMPLIFY_GEOM = No
    GEODATABASE_FILE_SIMPLIFY_NETWORK_FEATURES = no
    GEODATABASE_FILE_TRANSACTION = 0
    GEODATABASE_FILE_TRANSACTION_INTERVAL = 1000
    GEODATABASE_FILE_TRANSACTION_TYPE = TRANSACTIONS
    GEODATABASE_FILE_VALIDATE_FEATURES = no
    GEODATABASE_FILE_XY_SCALE = 0
    GEODATABASE_FILE_X_ORIGIN = 0
    GEODATABASE_FILE_Y_ORIGIN = 0
    GEODATABASE_FILE_Z_ORIGIN = 0
    GEODATABASE_FILE_Z_SCALE = 0
    TOTAL_FEATURES_WRITTEN_ATTR = _total_features_written

FME custom transformer Starter
This transformer is intended to start a workspace branch without the use of the creator transformer. This will end up without additional attributes (_creation_instance) at the end of the workspace.

Creator
    GEOMTYPE = Geometry Object
    NUM = 1
    CREATED -> Output (output)
Output (output)
