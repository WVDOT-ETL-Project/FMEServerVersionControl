FME workspace ETL_GTI_PUB.fmw

Parameters:
- pEnv = STG   # Select Database Environment
- pConcurrencyFGDB = \\dotb6gistest1\share\ArcGIS\Output\Route_Concurrency.gdb   # FGDB with "Concurrencies" Feature Class

Starter
    -> WV_Initiator
WV_Initiator
    pDOT_RouteScope = 0
    pEnv = $(pEnv)
    pHistoryCutOffDate = 20230101
    -> FTR_ROUTES [INITIATOR]
    -> FTR_COUNTY [INITIATOR]
    -> FTR_ROUTE_STATUS [INITIATOR]
    -> FTR_FUNCT [INITIATOR]
    -> FTR_NHS [INITIATOR]
    -> FTR_WVFUNCT [INITIATOR]
    -> FTR_Events [INITIATOR]
    -> FTR_SubRoutes [INITIATOR]

Bookmark: SubRoutes
FTR_SubRoutes: FeatureReader
    ATTRIBUTES = Concurrencies,"ObjectId,NetworkId,RouteId,SectionId,FromMeasure,ToMeasure,FromDate,ToDate,DominantFlag,DominantError"
    ATTR_ACCUM_MODE = Only Use Result
    COMBINE_GEOM = Use Result
    DATASET = $(pConcurrencyFGDB)
    FEATURETYPES = Concurrencies
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    INTERACT = NONE
    OUTPUT_FEATURES_DISPLAY = Schema and Data Features
    Concurrencies -> TST_SubRoutes
TST_SubRoutes: Tester
    BOOL_OP = AND
    TEST_CLAUSE:
      TEST @Value(DominantFlag) = 0
      TEST ToDate ATTRIBUTE_VALUE_NULL ""
    TEST_MODE = TEST
    PASSED -> ABK_SubRoutes
ABK_SubRoutes: AttributeKeeper
    CREATE_BULK_MODE_FEATURES = NO
    KEEP_ATTRS = FromMeasure,RouteId,ToMeasure
    -> Counter
Counter
    CNT_ATTR = _count
    DOMAIN = counter
    SCOPE = Global
    START = 0
    -> AttributeSwapper
AttributeSwapper
    ATTR_A = FromMeasure
    ATTR_B = ToMeasure
    COMP_MODE = Automatic
    CONDITION = A_GT_B
    -> LRS_EventMerger [Input_Event]
LRS_EventMerger
    pEvent_Attribute = RouteId
    pEvent_F_Meas = FromMeasure
    pEvent_ID = _count
    pEvent_Route_ID = RouteId
    pEvent_T_Meas = ToMeasure
    pPrecision = 5
    -> AttributeManager
AttributeManager
    ATTR_TABLE:
      REMOVE _oEventIDs{}._pEventID
      RENAME_SET_VALUE _oFMeas > FromMeasure
      RENAME_SET_VALUE _oTMeas > ToMeasure
      REMOVE _oMergedEventIDs
    -> LRS_GeoCoder_SubRoutes [LRS_Events]
LRS_GeoCoder_SubRoutes
    pEvent_F_Meas = FromMeasure
    pEvent_Route_ID = RouteId
    pEvent_T_Meas = ToMeasure
    pLRS_Route_ID = CO_ROUTEID
    pPrecision = 5
    LRS_Event_Features -> ABM_SubRoutes
ABM_SubRoutes: AttributeManager
    ATTR_TABLE:
      REMOVE _oFMeas
      REMOVE _oTMeas
      REMOVE FROMDATE
      REMOVE TODATE
      RENAME_SET_VALUE CO_CountyID > CountyCode
      RENAME_SET_VALUE CO_SignSystem > SignSystem
      RENAME_SET_VALUE CO_RouteNumber > Route
      RENAME_SET_VALUE CO_SubRoute > SubRoute
      RENAME_SET_VALUE CO_SuppCode > SuppCode
      REMOVE CO_RouteDirection
      REMOVE CO_ExitNumber
      REMOVE CO_RampLetter
      REMOVE CO_ROUTEID
      REMOVE SurveyDirection
      RENAME_SET_VALUE CO_RouteLabel > Label = FME_CONDITIONAL:DEFAULT_VALUE'@ReplaceRegularExpression(@Value(Route),^[0]*,,caseSensitive=TRUE)/@ReplaceRegularExpression(@Value(SubRoute),^[0]*,,caseSensitive=TRUE)'BOOL_OP;OR;COMPOSITE_TEST;1;TEST @Value(SubRoute) = 00'@ReplaceRegularExpression(@Value(Route),^[0]*,,caseSensitive=TRUE)'FME_NUM_CONDITIONS2___
      RENAME_SET_VALUE FromMeasure > BMP
      RENAME_SET_VALUE ToMeasure > EMP
      RENAME_SET_VALUE DISTRICTS > District = FME_CONDITIONAL:DEFAULT_VALUE'0@Value(District)'BOOL_OP;OR;COMPOSITE_TEST;1;TEST @Value(District) > 9'@Value(District)'FME_NUM_CONDITIONS2___
      REMOVE CO_CODE
    -> ABC_Connection_2
ABC_Connection_2: AttributeCreator
    ATTR_TABLE:
      SET_TO p_SdeCoon = FME_CONDITIONAL:DEFAULT_VALUE'\\dotb6gistest1\share\ArcGIS\Resources\Connections\fme@STG_SDE_GTI_PUB_UTM_STG.sde'BOOL_OP;OR;COMPOSITE_TEST;1;TEST $(pEnv) = PRD'\\dotb6gistest1\share\ArcGIS\Resources\Connections\fme@PRD_SDE_GTI_PUB_UTM.sde'FME_NUM_CONDITIONS2___
      SET_TO p_SdeCoon_WM = FME_CONDITIONAL:DEFAULT_VALUE'\\dotb6gistest1\share\ArcGIS\Resources\Connections\fme@STG_SDE_GTI_PUB_WM_STG.sde'BOOL_OP;OR;COMPOSITE_TEST;1;TEST $(pEnv) = PRD'\\dotb6gistest1\share\ArcGIS\Resources\Connections\fme@PRD_SDE_GTI_PUB_WM.sde'FME_NUM_CONDITIONS2___
    -> FTW_SubRoutes [FeatureClass1]
    -> FTW_SubRoutes_WM [FeatureClass1]
FTW_SubRoutes_WM: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon_WM)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_SubRoutes: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written

Bookmark: Lane_Info_RH
FTR_Events: FeatureReader
    ATTRIBUTES = RH.LRSE_AADT_evw,"OBJECTID,AADT_ID,ROUTE_ID,FROM_MEASURE,TO_MEASURE,AADT,AADT_YEAR,FUTURE_AADT,FUTURE_AADT_YEAR,PREVIOUS_AADT,AADT_ESCALATION_PCT,REAL_ESTIMATE,COUNT_CATEGORY,FIELD_ESTABLISH_DATE,SYSTEM_CREATE_DATE,SYSTEM_MOD_DATE,RH_FROM_DATE,RH_TO_DATE,USER_CREATE,USER_MOD,LocError,AADTT,K_Factor,D_Factor,GDB_GEOMATTR_DATA,SDE_STATE_ID",RH.LRSE_PAVEMENT_WIDTH_evw,"OBJECTID,PAVEMENT_WIDTH_ID,ROUTE_ID,FROM_MEASURE,TO_MEASURE,PAVEMENT_WIDTH_FT,FIELD_ESTABLISH_DATE,SYSTEM_CREATE_DATE,SYSTEM_MOD_DATE,RH_FROM_DATE,RH_TO_DATE,USER_CREATE,USER_MOD,LocError,GDB_GEOMATTR_DATA,SDE_STATE_ID",RH.LRSE_SURFACE_TYPE_evw,"OBJECTID,SURFACE_TYPE_ID,ROUTE_ID,FROM_MEASURE,TO_MEASURE,SURFACE_TYPE,FIELD_ESTABLISH_DATE,SYSTEM_CREATE_DATE,SYSTEM_MOD_DATE,RH_FROM_DATE,RH_TO_DATE,USER_CREATE,USER_MOD,LocError,GDB_GEOMATTR_DATA,SDE_STATE_ID"
    ATTRS_TO_EXPOSE = FROM_MEASURE TO_MEASURE AADT AADT_YEAR PAVEMENT_WIDTH_FT SURFACE_TYPE ROUTE_ID fme_feature_type
    ATTR_ACCUM_MODE = Only Use Result
    COMBINE_GEOM = Use Result
    DATASET = @Value(_connSQL_RIL_LRS_PUB)
    FEATURETYPES = RH.LRSE_AADT RH.LRSE_PAVEMENT_WIDTH RH.LRSE_SURFACE_TYPE
    FORMAT = MSSQL_SPATIAL
    INTERACT = NONE
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = @Value(_connSQL_RIL_LRS_PUB)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    WHERE = [RH_TO_DATE] IS NULL
    <OTHER> -> CNT_Events
CNT_Events: Counter
    CNT_ATTR = _count
    DOMAIN = counter
    SCOPE = Global
    START = 0
    -> LRS_EventLineOnLine_SS [LRS_Events]
    -> FTJ_Events [LEFT]
LRS_EventLineOnLine_SS
    pEvent_F_Meas = FROM_MEASURE
    pEvent_ID = _count
    pEvent_Route_ID = ROUTE_ID
    pEvent_T_Meas = TO_MEASURE
    pLayer_Name = fme_feature_type
    pPrecision = 3
    -> LSE_Overlayed
LSE_Overlayed: ListExploder
    ATTR_ACCUM_MODE = Merge List Attributes
    ATTR_CONFLICT_RES = Use List Attribute Values
    INDEX_ATTR = _element_index
    LIST_ATTR = _oEventIds{}
    ELEMENTS -> FTJ_Events [RIGHT]
FTJ_Events: FeatureJoiner
    ATTR_CONFLICT_RES = Prefer Left
    GEOMETRY_HANDLING = Prefer Left
    JOIN_KEYS = _count _pEvent_ID AUTO
    JOIN_MODE = Inner
    JOINED -> ABM_Joined
ABM_Joined: AttributeManager
    ATTR_TABLE:
      REMOVE FROM_MEASURE
      REMOVE TO_MEASURE
      REMOVE _count
      REMOVE _pEvent_Route_ID
      REMOVE _pEvent_ID
      REMOVE _element_index
    -> STC
STC: StatisticsCalculator
    CALCULATION_MODE = LEXICAL
    FEAT_STATS = PAVEMENT_WIDTH_FT,LEXICAL,MIN,,,<Unused>,<Unused>,,,,<Unused>,<Unused>,<Unused>,,;AADT,LEXICAL,MIN,,,<Unused>,<Unused>,,,,<Unused>,<Unused>,<Unused>,,;SURFACE_TYPE,LEXICAL,MIN,,,<Unused>,<Unused>,,,,<Unused>,<Unused>,<Unused>,,;AADT_YEAR,LEXICAL,MIN,,,<Unused>,<Unused>,,,,<Unused>,<Unused>,<Unused>,,
    GROUP_BY = _oFMeas _oTMeas ROUTE_ID
    SUMMARY -> BAR
BAR: BulkAttributeRenamer
    ATTRCHOICE = All Attributes
    CASE_DISP = YES
    MODE_CHOICE = RENAME
    PATTERN_ACTION_DISP = REMOVESUFFIX
    REPLACE_STR = .min
    -> ABM_Result
ABM_Result: AttributeManager
    ATTR_TABLE:
      RENAME_SET_VALUE _oFMeas > FROM_MEASURE
      RENAME_SET_VALUE _oTMeas > TO_MEASURE
    USER_EXPOSED_ATTRIBUTES = AADT_YEAR
    -> LRS_GeoCoder_LaneInfo [LRS_Events]
LRS_GeoCoder_LaneInfo
    pEvent_F_Meas = FROM_MEASURE
    pEvent_Route_ID = ROUTE_ID
    pEvent_T_Meas = TO_MEASURE
    pLRS_Route_ID = CO_ROUTEID
    pPrecision = 5
    LRS_Event_Features -> ABR_LaneInfo
ABR_LaneInfo: AttributeRemover
    REMOVE_ATTRS = _oFMeas,_oTMeas,CO_ROUTEID,FROMDATE,TODATE
    -> ABC_Connection
ABC_Connection: AttributeCreator
    ATTR_TABLE:
      SET_TO p_SdeCoon = FME_CONDITIONAL:DEFAULT_VALUE'\\dotb6gistest1\share\ArcGIS\Resources\Connections\fme@STG_SDE_GTI_PUB_UTM_STG.sde'BOOL_OP;OR;COMPOSITE_TEST;1;TEST $(pEnv) = PRD'\\dotb6gistest1\share\ArcGIS\Resources\Connections\fme@PRD_SDE_GTI_PUB_UTM.sde'FME_NUM_CONDITIONS2___
      SET_TO p_SdeCoon_WM = FME_CONDITIONAL:DEFAULT_VALUE'\\dotb6gistest1\share\ArcGIS\Resources\Connections\fme@STG_SDE_GTI_PUB_WM_STG.sde'BOOL_OP;OR;COMPOSITE_TEST;1;TEST $(pEnv) = PRD'\\dotb6gistest1\share\ArcGIS\Resources\Connections\fme@PRD_SDE_GTI_PUB_WM.sde'FME_NUM_CONDITIONS2___
    -> FTW_LaneInfo [FeatureClass1]
    -> FTW_LaneInfo_WM [FeatureClass1]
FTW_LaneInfo: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_LaneInfo_WM: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon_WM)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written

Bookmark: All Routes
FTR_ROUTES: FeatureReader
    ATTRIBUTES = RH.LRSN_COUNTY_MILEPOINT,"OBJECTID,FROMDATE,TODATE,CO_CountyID,CO_SignSystem,CO_RouteNumber,CO_SubRoute,CO_SuppCode,CO_RouteDirection,CO_ExitNumber,CO_RampLetter,CO_ROUTEID,SurveyDirection,CO_RouteLabel,GDB_GEOMATTR_DATA"
    ATTR_ACCUM_MODE = Only Use Result
    COMBINE_GEOM = Use Result
    DATASET = @Value(_connSQL_RIL_LRS_PUB)
    FEATURETYPES = RH.LRSN_COUNTY_MILEPOINT
    FORMAT = MSSQL_SPATIAL
    INTERACT = NONE
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = @Value(_connSQL_RIL_LRS_PUB)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    WHERE = [TODATE] IS NULL
    RH.LRSN_COUNTY_MILEPOINT -> ABK_Routes
ABK_Routes: AttributeKeeper
    CREATE_BULK_MODE_FEATURES = NO
    KEEP_ATTRS = CO_CountyID,CO_ExitNumber,CO_RampLetter,CO_RouteDirection,CO_ROUTEID,CO_RouteLabel,CO_RouteNumber,CO_SignSystem,CO_SubRoute,CO_SuppCode,FROMDATE,SurveyDirection,TODATE
    -> FTJ [LEFT]
    -> LRS_GeoCoder_LaneInfo [LRS_Route_Features]
FTR_COUNTY: FeatureReader
    ATTRIBUTES = RH.COUNTIES,"OBJECTID,AREA_,PERIMETER,DEP_24K_,DEP_24K_ID,NAME,STATE,FIPS,POP1986,POP2000,POP_CHNG,POPCH_PCT,MALES,FEMALES,AMER_IND,ASIAN,BLACK,HAWN_PL,HISPANIC,MULT_RACE,OTHER,WHITE,HOUSEHOLDS,AVG_HH_SZ,HSE_UNITS,OWNER_OCC,RENTER_OCC,VACANT,DISTRICTS,CO_CODE,GDB_GEOMATTR_DATA"
    ATTR_ACCUM_MODE = Only Use Result
    COMBINE_GEOM = Use Result
    DATASET = @Value(_connSQL_RIL_LRS_PUB)
    FEATURETYPES = RH.COUNTIES
    FORMAT = MSSQL_SPATIAL
    INTERACT = NONE
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = @Value(_connSQL_RIL_LRS_PUB)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    RH.COUNTIES -> ATK_COUNTY
ATK_COUNTY: AttributeKeeper
    CREATE_BULK_MODE_FEATURES = NO
    KEEP_ATTRS = CO_CODE,DISTRICTS
    -> FTJ [RIGHT]
    -> FTJ_DOMINANT [RIGHT]
FTJ: FeatureJoiner
    ATTR_CONFLICT_RES = Prefer Left
    GEOMETRY_HANDLING = Prefer Left
    JOIN_KEYS = CO_CountyID CO_CODE AUTO
    JOIN_MODE = Inner
    JOINED -> ABR
    JOINED -> LRS_GeoCoder_SubRoutes [LRS_Route_Features]
ABR: AttributeRemover
    REMOVE_ATTRS = CO_CODE
    -> ABC_LayerName
ABC_LayerName: AttributeCreator
    ATTR_TABLE:
      SET_TO LayerName = FME_CONDITIONAL:DEFAULT_VALUE'DBO.All_Routes_District_0@Value(DISTRICTS)'BOOL_OP;OR;COMPOSITE_TEST;1;TEST @Value(DISTRICTS) > 9'DBO.All_Routes_District_@Value(DISTRICTS)'FME_NUM_CONDITIONS2___
      SET_TO p_SdeCoon = FME_CONDITIONAL:DEFAULT_VALUE'\\dotb6gistest1\share\ArcGIS\Resources\Connections\fme@STG_SDE_GTI_PUB_UTM_STG.sde'BOOL_OP;OR;COMPOSITE_TEST;1;TEST $(pEnv) = PRD'\\dotb6gistest1\share\ArcGIS\Resources\Connections\fme@PRD_SDE_GTI_PUB_UTM.sde'FME_NUM_CONDITIONS2___
      SET_TO p_SdeCoon_WM = FME_CONDITIONAL:DEFAULT_VALUE'\\dotb6gistest1\share\ArcGIS\Resources\Connections\fme@STG_SDE_GTI_PUB_WM_STG.sde'BOOL_OP;OR;COMPOSITE_TEST;1;TEST $(pEnv) = PRD'\\dotb6gistest1\share\ArcGIS\Resources\Connections\fme@PRD_SDE_GTI_PUB_WM.sde'FME_NUM_CONDITIONS2___
    -> ABR_DISTRICTS
ABR_DISTRICTS: AttributeRemover
    REMOVE_ATTRS = DISTRICTS
    -> FTW_ALLROUTES [Output]
    -> FTW_ALLROUTES_Combined [Output]
    -> FTW_ALLROUTES_WM [Output]
    -> FTW_ALLROUTES_Combined_WM [Output]
FTW_ALLROUTES: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_ALLROUTES_WM: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon_WM)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_ALLROUTES_Combined_WM: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon_WM)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_ALLROUTES_Combined: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written

Bookmark: Dominant Routes
FTR_ROUTE_STATUS: FeatureReader
    ATTRIBUTES = RH.LRSE_ROUTE_STATUS,"OBJECTID,ROUTE_STATUS_ID,ROUTE_ID,FROM_MEASURE,TO_MEASURE,ROUTE_STATUS,FIELD_ESTABLISH_DATE,SYSTEM_CREATE_DATE,SYSTEM_MOD_DATE,RH_FROM_DATE,RH_TO_DATE,USER_CREATE,USER_MOD,LocError,GDB_GEOMATTR_DATA"
    ATTR_ACCUM_MODE = Only Use Result
    COMBINE_GEOM = Use Result
    DATASET = @Value(_connSQL_RIL_LRS_PUB)
    FEATURETYPES = RH.LRSE_ROUTE_STATUS
    FORMAT = MSSQL_SPATIAL
    INTERACT = NONE
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = @Value(_connSQL_RIL_LRS_PUB)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    WHERE = [RH_TO_DATE] IS NULL
    RH.LRSE_ROUTE_STATUS -> ABM_ROUTE_STATUS
ABM_ROUTE_STATUS: AttributeManager
    ATTR_TABLE:
      REMOVE OBJECTID
      REMOVE ROUTE_STATUS_ID
      RENAME_SET_VALUE ROUTE_ID > ROUTEID
      RENAME_SET_VALUE FROM_MEASURE > BMP
      RENAME_SET_VALUE TO_MEASURE > EMP
      REMOVE FIELD_ESTABLISH_DATE
      REMOVE SYSTEM_CREATE_DATE
      REMOVE SYSTEM_MOD_DATE
      REMOVE RH_FROM_DATE
      REMOVE RH_TO_DATE
      REMOVE USER_CREATE
      REMOVE USER_MOD
      REMOVE LocError
      REMOVE GDB_GEOMATTR_DATA
      SET_TO CountyCode = @Substring(@Value(ROUTEID),0,2)
      SET_TO Route = @Substring(@Value(ROUTEID),3,4)
      SET_TO SubRoute = @Substring(@Value(ROUTEID),7,2)
      SET_TO SuppCode = @Substring(@Value(ROUTEID),9,2)
      SET_TO SignSystem = @Substring(@Value(ROUTEID),2,1)
      SET_TO Label = FME_CONDITIONAL:DEFAULT_VALUE'@ReplaceRegularExpression(@Value(Route),^[0]*,,caseSensitive=TRUE)/@ReplaceRegularExpression(@Value(SubRoute),^[0]*,,caseSensitive=TRUE)'BOOL_OP;OR;COMPOSITE_TEST;1;TEST @Value(SubRoute) = 00'@ReplaceRegularExpression(@Value(Route),^[0]*,,caseSensitive=TRUE)'FME_NUM_CONDITIONS2___
    USER_EXPOSED_ATTRIBUTES = CountyCode
    -> FTJ_DOMINANT [LEFT]
FTJ_DOMINANT: FeatureJoiner
    ATTR_CONFLICT_RES = Prefer Left
    GEOMETRY_HANDLING = Prefer Left
    JOIN_KEYS = CountyCode CO_CODE AUTO
    JOIN_MODE = Inner
    JOINED -> ABM_Dominant
ABM_Dominant: AttributeManager
    ATTR_TABLE:
      SET_TO District = FME_CONDITIONAL:DEFAULT_VALUE'0@Value(DISTRICTS)'BOOL_OP;OR;COMPOSITE_TEST;1;TEST @Value(DISTRICTS) > 9'@Value(DISTRICTS)'FME_NUM_CONDITIONS2___
      SET_TO LayerName = DBO.Dominant_Routes_District_@Value(District)
      REMOVE DISTRICTS
      REMOVE CO_CODE
      SET_TO p_SdeCoon = FME_CONDITIONAL:DEFAULT_VALUE'\\dotb6gistest1\share\ArcGIS\Resources\Connections\fme@STG_SDE_GTI_PUB_UTM_STG.sde'BOOL_OP;OR;COMPOSITE_TEST;1;TEST $(pEnv) = PRD'\\dotb6gistest1\share\ArcGIS\Resources\Connections\fme@PRD_SDE_GTI_PUB_UTM.sde'FME_NUM_CONDITIONS2___
      SET_TO p_SdeCoon_WM = FME_CONDITIONAL:DEFAULT_VALUE'\\dotb6gistest1\share\ArcGIS\Resources\Connections\fme@STG_SDE_GTI_PUB_WM_STG.sde'BOOL_OP;OR;COMPOSITE_TEST;1;TEST $(pEnv) = PRD'\\dotb6gistest1\share\ArcGIS\Resources\Connections\fme@PRD_SDE_GTI_PUB_WM.sde'FME_NUM_CONDITIONS2___
    USER_EXPOSED_ATTRIBUTES = District
    -> FTW_DOMINANTROUTES [Output]
    -> FTW_DOMINANTROUTES_Combined [Output]
    -> FTW_DOMINANTROUTES_WM [Output]
    -> FTW_DOMINANTROUTES_Combined_WM [Output]
FTW_DOMINANTROUTES_WM: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon_WM)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_DOMINANTROUTES_Combined_WM: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon_WM)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_DOMINANTROUTES: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_DOMINANTROUTES_Combined: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written

Bookmark: Federal Functional Class Routes
FTR_FUNCT: FeatureReader
    ATTRIBUTES = RH.LRSE_NAT_FUNCT_CLASS,"OBJECTID,NAT_FUNCTIONAL_CLASS_ID,ROUTE_ID,FROM_MEASURE,TO_MEASURE,NAT_FUNCTIONAL_CLASS,FIELD_ESTABLISH_DATE,SYSTEM_CREATE_DATE,SYSTEM_MOD_DATE,RH_FROM_DATE,RH_TO_DATE,USER_CREATE,USER_MOD,LocError,GDB_GEOMATTR_DATA"
    ATTR_ACCUM_MODE = Only Use Result
    COMBINE_GEOM = Use Result
    DATASET = @Value(_connSQL_RIL_LRS_PUB)
    FEATURETYPES = RH.LRSE_NAT_FUNCT_CLASS
    FORMAT = MSSQL_SPATIAL
    INTERACT = NONE
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = @Value(_connSQL_RIL_LRS_PUB)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    WHERE = [RH_TO_DATE] IS NULL
    RH.LRSE_NAT_FUNCT_CLASS -> ATM_FUNCT
ATM_FUNCT: AttributeManager
    ATTR_TABLE:
      REMOVE OBJECTID
      REMOVE NAT_FUNCTIONAL_CLASS_ID
      REMOVE FIELD_ESTABLISH_DATE
      REMOVE SYSTEM_CREATE_DATE
      REMOVE SYSTEM_MOD_DATE
      REMOVE RH_FROM_DATE
      REMOVE RH_TO_DATE
      REMOVE USER_CREATE
      REMOVE USER_MOD
      REMOVE LocError
      REMOVE GDB_GEOMATTR_DATA
      SET_TO Length = @Evaluate(@Value(TO_MEASURE)-@Value(FROM_MEASURE))
      SET_TO p_SdeCoon = FME_CONDITIONAL:DEFAULT_VALUE'\\dotb6gistest1\share\ArcGIS\Resources\Connections\fme@STG_SDE_GTI_PUB_UTM_STG.sde'BOOL_OP;OR;COMPOSITE_TEST;1;TEST $(pEnv) = PRD'\\dotb6gistest1\share\ArcGIS\Resources\Connections\fme@PRD_SDE_GTI_PUB_UTM.sde'FME_NUM_CONDITIONS2___
      SET_TO p_SdeCoon_WM = FME_CONDITIONAL:DEFAULT_VALUE'\\dotb6gistest1\share\ArcGIS\Resources\Connections\fme@STG_SDE_GTI_PUB_WM_STG.sde'BOOL_OP;OR;COMPOSITE_TEST;1;TEST $(pEnv) = PRD'\\dotb6gistest1\share\ArcGIS\Resources\Connections\fme@PRD_SDE_GTI_PUB_WM.sde'FME_NUM_CONDITIONS2___
    -> ABR_FUNCT
ABR_FUNCT: AttributeRounder
    PLACES = 3
    ROUND_TYPE = Nearest
    SRC_ATTRS = Length
    -> FTW_FUNCT [Output]
    -> FTW_FUNCT_WM [Output]
FTW_FUNCT: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_FUNCT_WM: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon_WM)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written

Bookmark: NHS
FTR_NHS: FeatureReader
    ATTRIBUTES = RH.LRSE_NHS,"OBJECTID,NHS_ID,ROUTE_ID,FROM_MEASURE,TO_MEASURE,NHS,NHS_APPROVED_DATE,FIELD_ESTABLISH_DATE,SYSTEM_CREATE_DATE,SYSTEM_MOD_DATE,RH_FROM_DATE,RH_TO_DATE,USER_CREATE,USER_MOD,LocError,GDB_GEOMATTR_DATA"
    ATTR_ACCUM_MODE = Only Use Result
    COMBINE_GEOM = Use Result
    DATASET = @Value(_connSQL_RIL_LRS_PUB)
    FEATURETYPES = RH.LRSE_NHS
    FORMAT = MSSQL_SPATIAL
    INTERACT = NONE
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = @Value(_connSQL_RIL_LRS_PUB)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    WHERE = [NHS]>0 AND [RH_TO_DATE] IS NULL
    RH.LRSE_NHS -> ATM_NHS
ATM_NHS: AttributeManager
    ATTR_TABLE:
      REMOVE OBJECTID
      REMOVE NHS_ID
      REMOVE NHS_APPROVED_DATE
      REMOVE FIELD_ESTABLISH_DATE
      REMOVE SYSTEM_CREATE_DATE
      REMOVE SYSTEM_MOD_DATE
      REMOVE RH_FROM_DATE
      REMOVE RH_TO_DATE
      REMOVE USER_CREATE
      REMOVE USER_MOD
      REMOVE LocError
      REMOVE GDB_GEOMATTR_DATA
      SET_TO Length = @Evaluate(@Value(TO_MEASURE)-@Value(FROM_MEASURE))
      SET_TO p_SdeCoon = FME_CONDITIONAL:DEFAULT_VALUE'\\dotb6gistest1\share\ArcGIS\Resources\Connections\fme@STG_SDE_GTI_PUB_UTM_STG.sde'BOOL_OP;OR;COMPOSITE_TEST;1;TEST $(pEnv) = PRD'\\dotb6gistest1\share\ArcGIS\Resources\Connections\fme@PRD_SDE_GTI_PUB_UTM.sde'FME_NUM_CONDITIONS2___
      SET_TO p_SdeCoon_WM = FME_CONDITIONAL:DEFAULT_VALUE'\\dotb6gistest1\share\ArcGIS\Resources\Connections\fme@STG_SDE_GTI_PUB_WM_STG.sde'BOOL_OP;OR;COMPOSITE_TEST;1;TEST $(pEnv) = PRD'\\dotb6gistest1\share\ArcGIS\Resources\Connections\fme@PRD_SDE_GTI_PUB_WM.sde'FME_NUM_CONDITIONS2___
    -> ABR_NHS
ABR_NHS: AttributeRounder
    PLACES = 3
    ROUND_TYPE = Nearest
    SRC_ATTRS = Length
    -> FTW_NHS [Output]
    -> FTW_NHS_WM [Output]
FTW_NHS: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_NHS_WM: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon_WM)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written

Bookmark: State Functional Class Routes
FTR_WVFUNCT: FeatureReader
    ATTRIBUTES = RH.LRSE_STATE_FUNCT_CLASS,"OBJECTID,STATE_FUNCTIONAL_CLASS_ID,ROUTE_ID,FROM_MEASURE,TO_MEASURE,STATE_FUNCTIONAL_CLASS,FIELD_ESTABLISH_DATE,SYSTEM_CREATE_DATE,SYSTEM_MOD_DATE,RH_FROM_DATE,RH_TO_DATE,USER_CREATE,USER_MOD,LocError,GDB_GEOMATTR_DATA"
    ATTR_ACCUM_MODE = Only Use Result
    COMBINE_GEOM = Use Result
    DATASET = @Value(_connSQL_RIL_LRS_PUB)
    FEATURETYPES = RH.LRSE_STATE_FUNCT_CLASS
    FORMAT = MSSQL_SPATIAL
    INTERACT = NONE
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = @Value(_connSQL_RIL_LRS_PUB)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    WHERE = [RH_TO_DATE] IS NULL
    RH.LRSE_STATE_FUNCT_CLASS -> ATM_WVFUNCT
ATM_WVFUNCT: AttributeManager
    ATTR_TABLE:
      REMOVE OBJECTID
      REMOVE FIELD_ESTABLISH_DATE
      REMOVE SYSTEM_CREATE_DATE
      REMOVE SYSTEM_MOD_DATE
      REMOVE RH_FROM_DATE
      REMOVE RH_TO_DATE
      REMOVE USER_CREATE
      REMOVE USER_MOD
      REMOVE LocError
      REMOVE GDB_GEOMATTR_DATA
      REMOVE STATE_FUNCTIONAL_CLASS_ID
      SET_TO Length = @Evaluate(@Value(TO_MEASURE)-@Value(FROM_MEASURE))
      SET_TO p_SdeCoon = FME_CONDITIONAL:DEFAULT_VALUE'\\dotb6gistest1\share\ArcGIS\Resources\Connections\fme@STG_SDE_GTI_PUB_UTM_STG.sde'BOOL_OP;OR;COMPOSITE_TEST;1;TEST $(pEnv) = PRD'\\dotb6gistest1\share\ArcGIS\Resources\Connections\fme@PRD_SDE_GTI_PUB_UTM.sde'FME_NUM_CONDITIONS2___
      SET_TO p_SdeCoon_WM = FME_CONDITIONAL:DEFAULT_VALUE'\\dotb6gistest1\share\ArcGIS\Resources\Connections\fme@STG_SDE_GTI_PUB_WM_STG.sde'BOOL_OP;OR;COMPOSITE_TEST;1;TEST $(pEnv) = PRD'\\dotb6gistest1\share\ArcGIS\Resources\Connections\fme@PRD_SDE_GTI_PUB_WM.sde'FME_NUM_CONDITIONS2___
    USER_EXPOSED_ATTRIBUTES = NAT_FUNCTIONAL_CLASS_ID,NAT_FUNCTIONAL_CLASS
    -> ABR_WVFUNCT
ABR_WVFUNCT: AttributeRounder
    PLACES = 3
    ROUND_TYPE = Nearest
    SRC_ATTRS = Length
    -> FTW_WVFUNCT [Output]
    -> FTW_WVFUNCT_WM [Output]
FTW_WVFUNCT: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
FTW_WVFUNCT_WM: FeatureWriter
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = @Value(p_SdeCoon_WM)
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written

FME custom transformer Starter
This transformer is intended to start a workspace branch without the use of the creator transformer. This will end up without additional attributes (_creation_instance) at the end of the workspace.

Creator
    GEOMTYPE = Geometry Object
    NUM = 1
    CREATED -> Output (output)
Output (output)

FME custom transformer AttributeSwapper
Swaps the values and internal storage data types of specified two attributes (A and B).
By default, swapping will be performed unconditionally, but optionally you can choose one of these conditional swapping modes. 
"A < B" [A_LT_B]: Swap the values only when A is less than B. 
"A > B" [A_GT_B]: Swap the values only when A is greater than B. 
Leading/trailing spaces and leading zeros will be ignored when the values are being compared as NUMERIC; will NOT be ignored when the values are being compared as STRING.
The <null> and <missing> will also be swapped, but those will be treated as the empty string when comparing values in conditional swapping mode. 
A new attribute called "_swapped" will be added to the output features; its value indicates whether the two attribute values have been swapped. 
_swapped = 1: the values have been swapped. 
_swapped = 0: the values have not been swapped.
Only when you set "A < B" or "A > B" to the "Swapping Condition" parameter and set "Numeric" to the "Comparison Mode" parameter, the input feature will be output via the <Rejected> port if a specified attribute stores a non-numeric value.
Parameters 
Attribute A / Attribute B : 
Select two attributes whose values should be swapped. 
Swap Condition :
Select one of these swapping condition. 
"Unconditional" [UNCONDITIONAL]: Swap the values unconditionally (default). 
"A < B" [A_LT_B]: Swap the values only when A is less than B. 
"A > B" [A_GT_B]: Swap the values only when A is greater than B. 
Comparison Mode :
Select one of these comparison mode for conditional swapping. This parameter setting will be just ignored when you have set "Unconditional" to the "Swap Condition" parameter.
"Automatic": The transformer will compare the values as numeric values if possible, and as strings otherwise. 
"String": The transformer will always compare the values as strings.
"Numeric": The transformer will always compare the values as numeric values. If a value is not numeric, the input feature will be output via the <Rejected> port (only when you have set "A < B" or "A > B" to the "Swap Condition" parameter).

Parameters:
- ATTR_A =   # " " Attribute A
- ATTR_B =   # " " Attribute B
- CONDITION = UNCONDITIONAL   # < B,A_LT_B%A > B,A_GT_B Swap Condition
- COMP_MODE = Automatic   # Comparison Mode

Input (input)
    -> ParameterFetcher
ParameterFetcher
    ATTR_LIST = __attributeswapper.attr_a {$(ATTR_A)} __attributeswapper.attr_b {$(ATTR_B)} __attributeswapper.condition {$(CONDITION)} __attributeswapper.comp_mode {$(COMP_MODE)}
    -> TclCaller
TclCaller
    SRC:
      proc swapAttributes {} {
          set result -1
          set attr_a [FME_GetAttribute "__attributeswapper.attr_a"]
          set attr_b [FME_GetAttribute "__attributeswapper.attr_b"]
          set condition [FME_GetAttribute "__attributeswapper.condition"]
          if {[string equal $condition "UNCONDITIONAL"]} {
              set result 1
          } else {
              proc trimLeftZero {s} {
                  set v [string trimleft [set t [string trim $s]] {0}]
                  if {[string length $v]==0 && 0<[string length $t]} {
                      return 0
                  } else {
                      return $v
                  }
              }
              set a [FME_GetAttribute $attr_a]
              set b [FME_GetAttribute $attr_b]
              set mode [FME_GetAttribute "__attributeswapper.comp_mode"]
              switch $mode {
                  "String" {
                      switch $condition {
                          "A_LT_B" {set result [expr [string compare $a $b] < 0]}
                          "A_GT_B" {set result [expr [string compare $a $b] > 0]}
                      }
                  }
                  default {
                      set x [trimLeftZero $a]
                      set y [trimLeftZero $b]
                      if {[string is double -strict $x] && [string is double -strict $y]} {
                          switch $condition {
                              "A_LT_B" {set result [expr $x < $y]}
                              "A_GT_B" {set result [expr $x > $y]}
                          }
                      } elseif {[string equal $mode "Automatic"]} {
                          switch $condition {
                              "A_LT_B" {set result [expr [string compare $a $b] < 0]}
                              "A_GT_B" {set result [expr [string compare $a $b] > 0]}
                          }
                      }
                  }
              }
          }
          if {$result == 1} {
              FME_RenameAttribute "__attributeswapper.tmp" $attr_a
              FME_RenameAttribute $attr_a $attr_b
              FME_RenameAttribute $attr_b "__attributeswapper.tmp"
          }
          return $result
      }
    TCLPROG = swapAttributes
    VAL_ATTR = _swapped
    -> Tester
Tester
    BOOL_OP = OR
    TEST_CLAUSE = TEST 0 <= @Value(_swapped)
    TEST_MODE = Automatic
    PASSED -> Output (output)
    FAILED -> <Rejected> (output)
Output (output)
<Rejected> (output)
