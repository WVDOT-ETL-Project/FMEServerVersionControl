FME workspace Report_Road_Summary.fmw
Title: WV_ETL_General
Description: Road Network Summary Report
History: 2023/04/01,Gistic,Initial release

Parameters:
- pEnv = PRD   # Select Database Environment
- pRouteIDSignSystem = 1 2 3 4
- pRouteIDPattern = 3%   # Enter Route ID Pattern (see instruction below)
- pFormatOutput = FILEGDB   # GDB,FILEGDB Select an output format
- pObserveDate =   # Observation Date (Blank for today)
- FME_SHAREDRESOURCE_TEMP = \\DOTB6GISTEST1\share\ReportOutput   # FME Server Temporary Resource Directory

Creator
    GEOMTYPE = Geometry Object
    NUM = 1
    CREATED -> WV_Initiator
Note: Make sure the pass the current parameters to the CT!!!
WV_Initiator
    pDOT_RouteScope = 0
    pEnv = $(pEnv)
    pObserveDate = $(pObserveDate)
    pRouteIDPattern = $(pRouteIDPattern)
    pRouteIDSignSystem = $(pRouteIDSignSystem)
    -> FRD_SDE_RIL_LRS_3 [INITIATOR]
    -> FRD_SDE_RIL_LRS [INITIATOR]
    -> FRD_SDE_RIL_LRS_2 [INITIATOR]

Bookmark: LRS Overlay and Geocoding
FRD_SDE_RIL_LRS_2: FeatureReader
    ATTRIBUTES = RH.LRSE_DISTRICT,"OBJECTID,DISTRICT_ID,ROUTE_ID,FROM_MEASURE,TO_MEASURE,DISTRICT,FIELD_ESTABLISH_DATE,SYSTEM_CREATE_DATE,SYSTEM_MOD_DATE,RH_FROM_DATE,RH_TO_DATE,USER_CREATE,USER_MOD,LocError,GDB_GEOMATTR_DATA",RH.LRSE_FEDERAL_AID,"OBJECTID,FEDERAL_AID_ID,ROUTE_ID,FROM_MEASURE,TO_MEASURE,FAS_TYPE,FIELD_ESTABLISH_DATE,SYSTEM_CREATE_DATE,SYSTEM_MOD_DATE,RH_FROM_DATE,RH_TO_DATE,USER_CREATE,USER_MOD,LocError,GDB_GEOMATTR_DATA",RH.LRSE_MAINT_OPERATIONS,"OBJECTID,MAINT_OPERATIONS_ID,ROUTE_ID,FROM_MEASURE,TO_MEASURE,SERVICE_ORG,SECTION_TYPE,IDENT,RTSIGN_NAME,LOCATION,COMMENTS,COMMENTS2,FIELD_ESTABLISH_DATE,SYSTEM_CREATE_DATE,SYSTEM_MOD_DATE,RH_FROM_DATE,RH_TO_DATE,USER_CREATE,USER_MOD,LocError,DISTRICT,Name,GDB_GEOMATTR_DATA",RH.LRSE_NHS,"OBJECTID,NHS_ID,ROUTE_ID,FROM_MEASURE,TO_MEASURE,NHS,NHS_APPROVED_DATE,FIELD_ESTABLISH_DATE,SYSTEM_CREATE_DATE,SYSTEM_MOD_DATE,RH_FROM_DATE,RH_TO_DATE,USER_CREATE,USER_MOD,LocError,GDB_GEOMATTR_DATA",RH.LRSE_STATE_FUNCT_CLASS,"OBJECTID,STATE_FUNCTIONAL_CLASS_ID,ROUTE_ID,FROM_MEASURE,TO_MEASURE,STATE_FUNCTIONAL_CLASS,FIELD_ESTABLISH_DATE,SYSTEM_CREATE_DATE,SYSTEM_MOD_DATE,RH_FROM_DATE,RH_TO_DATE,USER_CREATE,USER_MOD,LocError,GDB_GEOMATTR_DATA",RH.LRSE_SURFACE_TYPE,"OBJECTID,SURFACE_TYPE_ID,ROUTE_ID,FROM_MEASURE,TO_MEASURE,SURFACE_TYPE,FIELD_ESTABLISH_DATE,SYSTEM_CREATE_DATE,SYSTEM_MOD_DATE,RH_FROM_DATE,RH_TO_DATE,USER_CREATE,USER_MOD,LocError,GDB_GEOMATTR_DATA"
    ATTRS_TO_EXPOSE = OBJECTID ROUTE_ID RH_FROM_DATE RH_TO_DATE FROM_MEASURE TO_MEASURE fme_feature_type STATE_FUNCTIONAL_CLASS FACILITY SURFACE_TYPE NHS SURFACE_TYPE_resolved NHS_resolved STATE_FUNCTIONAL_CLASS_resolved FACILITY_resolved
    ATTR_ACCUM_MODE = Only Use Result
    COMBINE_GEOM = Use Initiator
    FEATURETYPES = RH.LRSE_NHS RH.LRSE_FACILITY RH.LRSE_STATE_FUNCT_CLASS RH.LRSE_SURFACE_TYPE
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = yes
    GEODATABASE_SDE_RESOLVE_SUBTYPE_NAMES = no
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = sde.DEFAULT
    GEODATABASE_SDE_VERSION_TYPE = Transactional Version
    INTERACT = NONE
    OUTPUT_FEATURES_DISPLAY = Schema and Data Features
    WHERE = @Value(_filter_event_by_observe_date_route_pattern)
    <OTHER> -> Counter
Counter
    CNT_ATTR = _count
    DOMAIN = counter
    SCOPE = Global
    START = 0
    -> LRS_EventLineOnLine_SS [LRS_Events]
    -> FeatureJoiner [LEFT]
LRS_EventLineOnLine_SS
    pEvent_F_Meas = FROM_MEASURE
    pEvent_ID = _count
    pEvent_Route_ID = ROUTE_ID
    pEvent_T_Meas = TO_MEASURE
    pLayer_Name = fme_feature_type
    pPrecision = 3
    -> ListExploder
ListExploder
    ATTR_ACCUM_MODE = Merge List Attributes
    ATTR_CONFLICT_RES = Use List Attribute Values
    INDEX_ATTR = _element_index
    LIST_ATTR = _oEventIds{}
    ELEMENTS -> FeatureJoiner [RIGHT]
FeatureJoiner
    ATTR_CONFLICT_RES = Prefer Left
    GEOMETRY_HANDLING = Prefer Left
    JOIN_KEYS = _count _pEvent_ID AUTO
    JOIN_MODE = Inner
    JOINED -> AttributeManager
AttributeManager
    ATTR_TABLE:
      REMOVE FROM_MEASURE
      REMOVE TO_MEASURE
      REMOVE RH_FROM_DATE
      REMOVE RH_TO_DATE
      REMOVE _count
      REMOVE _pEvent_Route_ID
      REMOVE _pEvent_ID
      REMOVE _element_index
    -> StatisticsCalculator
StatisticsCalculator
    CALCULATION_MODE = LEXICAL
    FEAT_STATS = NHS_resolved,LEXICAL,MIN,,,<Unused>,<Unused>,,,,<Unused>,<Unused>,<Unused>,,;FACILITY_resolved,LEXICAL,MIN,,,<Unused>,<Unused>,,,,<Unused>,<Unused>,<Unused>,,;STATE_FUNCTIONAL_CLASS_resolved,LEXICAL,MIN,,,<Unused>,<Unused>,,,,<Unused>,<Unused>,<Unused>,,;SURFACE_TYPE,LEXICAL,MIN,,,<Unused>,<Unused>,,,,<Unused>,<Unused>,<Unused>,,
    GROUP_BY = _oFMeas _oTMeas ROUTE_ID
    SUMMARY -> BulkAttributeRenamer
BulkAttributeRenamer
    ATTRCHOICE = All Attributes
    CASE_DISP = YES
    MODE_CHOICE = RENAME
    PATTERN_ACTION_DISP = REMOVESUFFIX
    REPLACE_STR = _resolved.min
    -> AttributeManager_2
AttributeManager_2
    ATTR_TABLE:
      SET_TO SURFACE_TYPE = FME_CONDITIONAL:DEFAULT_VALUE'Unimproved'BOOL_OP;OR;COMPOSITE_TEST;1;NUM_TEST @Value(SURFACE_TYPE.min) RANGE [6,13]'Paved'BOOL_OP;OR;COMPOSITE_TEST;1;NUM_TEST @Value(SURFACE_TYPE.min) RANGE [3,5]'Unpaved'FME_NUM_CONDITIONS3___
      REMOVE SURFACE_TYPE.min
    -> LRS_GeoCoder [LRS_Events]
FRD_SDE_RIL_LRS_3: FeatureReader
    ATTRIBUTES = RH.LRSN_COUNTY_MILEPOINT,"OBJECTID,FROMDATE,TODATE,CO_CountyID,CO_SignSystem,CO_RouteNumber,CO_SubRoute,CO_SuppCode,CO_RouteDirection,CO_ExitNumber,CO_RampLetter,CO_ROUTEID,SurveyDirection,CO_RouteLabel,SHAPE.STLength()"
    ATTR_ACCUM_MODE = Only Use Result
    COMBINE_GEOM = Use Result
    FEATURETYPES = RH.LRSN_COUNTY_MILEPOINT
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = sde.DEFAULT
    GEODATABASE_SDE_VERSION_TYPE = Transactional Version
    INTERACT = NONE
    OUTPUT_FEATURES_DISPLAY = Data Features
    WHERE = @Value(_filter_route_by_observe_date_route_pattern)
    RH.LRSN_COUNTY_MILEPOINT -> AttributeKeeper_2
AttributeKeeper_2
    CREATE_BULK_MODE_FEATURES = NO
    KEEP_ATTRS = CO_CountyID,CO_ROUTEID,CO_SignSystem
    -> LRS_GeoCoder [LRS_Route_Features]
LRS_GeoCoder
    pEvent_F_Meas = _oFMeas
    pEvent_Route_ID = ROUTE_ID
    pEvent_T_Meas = _oTMeas
    pLRS_Route_ID = CO_ROUTEID
    pPrecision = 3
    LRS_Event_Features -> AttributeManager_9
AttributeManager_9
    ATTR_TABLE:
      RENAME_SET_VALUE _oFMeas > FROM_MEASURE
      RENAME_SET_VALUE _oTMeas > TO_MEASURE
      SET_TO seg_length = @round(@Value(TO_MEASURE)-@Value(FROM_MEASURE), 3)
    USER_EXPOSED_ATTRIBUTES = NHS,NHS_resolved,fme_feature_type
    -> AttributeKeeper
    -> FeatureJoiner_4 [LEFT]

Bookmark: Write GIS
AttributeKeeper
    CREATE_BULK_MODE_FEATURES = NO
    KEEP_ATTRS = FACILITY,NHS,STATE_FUNCTIONAL_CLASS,SURFACE_TYPE,fme_feature_type,FROM_MEASURE,ROUTE_ID,TO_MEASURE
    -> AttributeCreator
AttributeCreator
    ATTR_TABLE:
      SET_TO fme_feature_type = route_seg
      SET_TO fme_feature_type_name = @Value(fme_feature_type)
    -> SchemaScanner
SchemaScanner
    CASE = No
    EMPTY_ATTR_HANDLING = IGNORE
    HOLD = Yes
    SCHEMA_NAME_ATTR = fme_feature_type_name
    UNBOUNDED_NUMBERS = Yes
    UNBOUNDED_STRINGS = No
    -> FeatureMerger [REQUESTOR]
    <SCHEMA> -> FWT-Output-GIS [Output]
Note: serialize the two writers so that they will not be over-written
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FWT-Output-GIS [Output]
Note: remove some internal columns
FWT-Output-GIS: FeatureWriter
    DATASET = $(FME_SHAREDRESOURCE_TEMP)\$(WORKSPACE_NAME)-$(pEnv)
    DATASET_ATTR = _dataset
    FEATURE_TYPE_LIST_ATTR = _feature_types
    FORMAT = GENERIC
    GENERIC_DESTINATION_DATASETTYPE_VALIDATION = Yes
    GENERIC_FORMAT = $(pFormatOutput)
    GENERIC_MIME_TYPE = text/plain
    TOTAL_FEATURES_WRITTEN_ATTR = _total_features_written

Bookmark: Domain Support
Note: county and district lookup
FRD_SDE_RIL_LRS: FeatureReader
    ATTRIBUTES = RH.Counties,"OBJECTID,AREA_,PERIMETER,DEP_24K_,DEP_24K_ID,NAME,STATE,FIPS,POP1986,POP2000,POP_CHNG,POPCH_PCT,MALES,FEMALES,AMER_IND,ASIAN,BLACK,HAWN_PL,HISPANIC,MULT_RACE,OTHER,WHITE,HOUSEHOLDS,AVG_HH_SZ,HSE_UNITS,OWNER_OCC,RENTER_OCC,VACANT,DISTRICTS,CO_CODE,SHAPE.STArea(),SHAPE.STLength()"
    ATTR_ACCUM_MODE = Only Use Result
    COMBINE_GEOM = Use Initiator
    FEATURETYPES = RH.Counties
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = sde.DEFAULT
    GEODATABASE_SDE_VERSION_TYPE = Transactional Version
    INTERACT = NONE
    OUTPUT_FEATURES_DISPLAY = Data Features
    RH.Counties -> AttributeKeeper_7
AttributeKeeper_7
    CREATE_BULK_MODE_FEATURES = NO
    KEEP_ATTRS = CO_CODE,DISTRICTS,NAME,_path_report_output,_suffix_output_report
    -> FeatureJoiner_4 [RIGHT]
FeatureJoiner_4
    ATTR_CONFLICT_RES = Prefer Left
    GEOMETRY_HANDLING = Prefer Left
    JOIN_KEYS = CO_CountyID CO_CODE AUTO
    JOIN_MODE = Inner
    JOINED -> AttributeManager_7
AttributeManager_7
    ATTR_TABLE:
      RENAME_SET_VALUE NAME > COUNTY
      RENAME_SET_VALUE DISTRICTS > DISTRICT
      RENAME_SET_VALUE seg_length > MILES = @round(@Value(MILES),3)
      REMOVE CO_CountyID
      REMOVE CO_SignSystem
      REMOVE CO_ROUTEID
    USER_EXPOSED_ATTRIBUTES = seg_length,_county_code,_sign_system,NHS_resolved,fme_feature_type,Desc,Code,Category
    -> GeometryRemover_2
GeometryRemover_2
    -> Junction

Bookmark: Excel Report Customization
Junction
    -> AttributeManager_10
    -> StatisticsCalculator_2
    -> StatisticsCalculator_3
    -> StatisticsCalculator_4
    -> StatisticsCalculator_5
    -> StatisticsCalculator_6
AttributeManager_10
    ATTR_TABLE = SET_TO _report_name = Summary Source
    USER_EXPOSED_ATTRIBUTES = SIGN_SYSTEM
    -> Sorter_6
Sorter_6
    SORT_PARM = DISTRICT NATURAL ASCENDING CO_CODE NATURAL ASCENDING STATE_FUNCTIONAL_CLASS NATURAL ASCENDING NHS NATURAL ASCENDING SURFACE_TYPE NATURAL ASCENDING
    SORTED -> FWT-Output-Excel [Output00]
StatisticsCalculator_2
    CALCULATION_MODE = NUMERIC
    FEAT_STATS = MILES,NUMERIC_MODE,,,COUNT,SUM,,,,,,,,,
    GROUP_BY = SURFACE_TYPE
    SUMMARY -> AttributeManager_3
AttributeManager_3
    ATTR_TABLE:
      RENAME_SET_VALUE MILES.total_count > FREQUENCY
      RENAME_SET_VALUE MILES.sum > SUM_LENGTH
      SET_TO _report_name = By_SurfaceType
    -> Sorter
Sorter
    SORT_PARM = SURFACE_TYPE NATURAL ASCENDING
    SORTED -> FWT-Output-Excel [Output]
StatisticsCalculator_3
    CALCULATION_MODE = NUMERIC
    FEAT_STATS = MILES,NUMERIC_MODE,,,COUNT,SUM,,,,,,,,,
    GROUP_BY = SURFACE_TYPE COUNTY
    SUMMARY -> AttributeManager_4
AttributeManager_4
    ATTR_TABLE:
      RENAME_SET_VALUE MILES.total_count > FREQUENCY
      RENAME_SET_VALUE MILES.sum > SUM_LENGTH
      SET_TO _report_name = By_SurfaceType_And_County
    -> Sorter_2
Sorter_2
    SORT_PARM = COUNTY NATURAL ASCENDING SURFACE_TYPE NATURAL ASCENDING
    SORTED -> FWT-Output-Excel [Sorted]
StatisticsCalculator_4
    CALCULATION_MODE = NUMERIC
    FEAT_STATS = MILES,NUMERIC_MODE,,,COUNT,SUM,,,,,,,,,
    GROUP_BY = COUNTY STATE_FUNCTIONAL_CLASS
    SUMMARY -> AttributeManager_5
AttributeManager_5
    ATTR_TABLE:
      RENAME_SET_VALUE MILES.total_count > FREQUENCY
      RENAME_SET_VALUE MILES.sum > SUM_LENGTH
      SET_TO _report_name = By_FC_And_County
    -> Sorter_3
Sorter_3
    SORT_PARM = COUNTY NATURAL ASCENDING STATE_FUNCTIONAL_CLASS NATURAL ASCENDING
    SORTED -> FWT-Output-Excel [Sorted00]
StatisticsCalculator_5
    CALCULATION_MODE = NUMERIC
    FEAT_STATS = MILES,NUMERIC_MODE,,,COUNT,SUM,,,,,,,,,
    GROUP_BY = COUNTY
    SUMMARY -> AttributeManager_6
AttributeManager_6
    ATTR_TABLE:
      RENAME_SET_VALUE MILES.total_count > FREQUENCY
      RENAME_SET_VALUE MILES.sum > SUM_LENGTH
      SET_TO _report_name = By_County
    -> Sorter_4
Sorter_4
    SORT_PARM = COUNTY NATURAL ASCENDING
    SORTED -> FWT-Output-Excel [Sorted01]
StatisticsCalculator_6
    CALCULATION_MODE = NUMERIC
    FEAT_STATS = MILES,NUMERIC_MODE,,,COUNT,SUM,,,,,,,,,
    GROUP_BY = COUNTY STATE_FUNCTIONAL_CLASS SURFACE_TYPE
    SUMMARY -> AttributeManager_8
AttributeManager_8
    ATTR_TABLE:
      RENAME_SET_VALUE MILES.total_count > FREQUENCY
      RENAME_SET_VALUE MILES.sum > SUM_LENGTH
      SET_TO _report_name = By_County_FClass_SufType
    -> Sorter_5
Sorter_5
    SORT_PARM = COUNTY NATURAL ASCENDING STATE_FUNCTIONAL_CLASS NATURAL ASCENDING SURFACE_TYPE NATURAL ASCENDING
    SORTED -> FWT-Output-Excel [Sorted02]
FWT-Output-Excel: FeatureWriter
    DATASET = $(FME_SHAREDRESOURCE_TEMP)\$(WORKSPACE_NAME)-$(pEnv)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
    SUMMARY -> AttributeKeeper_4
AttributeKeeper_4
    CREATE_BULK_MODE_FEATURES = NO
    -> FeatureMerger [SUPPLIER]
