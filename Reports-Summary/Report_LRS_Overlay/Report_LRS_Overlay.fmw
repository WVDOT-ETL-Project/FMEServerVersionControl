FME workspace Report_LRS_Overlay.fmw
Description: This workspace supports the LRS Overlay Self Report part in the Report Portal. It is designed for use by the web UI.
History: 2023/04/04,Gistic,Initial release,2023/04/25,Bo,Use single Excel writer; correct DS writing pattern ,2023/04/08,BG/Jia,add email function, add support for FGDB

Parameters:
- pEnv = PRD   # Select Database Environment
- pRouteIDSignSystem = 1
- pLayers = RH.LRSE_AADT RH.LRSE_ACCESS_CONTROL RH.LRSE_ALT_ROUTE_NAME   # Select Layers to Overlay
- pAttributes = AADT FACILITY NAT_FUNCTIONAL_CLASS   # Corresponding Attributes
- pSumDims = COUNTY FACILITY   # Summarizing Dimensions
- pRouteIDCounty = 01
- pFormatOutput = NONE   # GDB,FILEGDB Select an output format
- FME_SHAREDRESOURCE_TEMP = \\dotb6gistest1\share\ReportOutput   # FME Server Temporary Resource Directory

Creator
    GEOMTYPE = Geometry Object
    NUM = 1
    CREATED -> WV_Initiator
WV_Initiator
    pDOT_RouteScope = 0
    pEnv = $(pEnv)
    pOutfileSuffix = " "
    pRouteIDCounty = $(pRouteIDCounty)
    pRouteIDPattern = %
    pRouteIDSignSystem = $(pRouteIDSignSystem)
    -> AttributeCreator_7
AttributeCreator_7
    ATTR_TABLE = SET_TO _pLayers = @ReplaceString($(pLayers), ,_evw ,caseSensitive=TRUE)_evw
    -> FRD_SQL_RIL_LRS [INITIATOR]
FRD_SQL_RIL_LRS: FeatureReader
    ATTRIBUTES = RH.LRSE_DISTRICT,"OBJECTID,DISTRICT_ID,ROUTE_ID,FROM_MEASURE,TO_MEASURE,DISTRICT,FIELD_ESTABLISH_DATE,SYSTEM_CREATE_DATE,SYSTEM_MOD_DATE,RH_FROM_DATE,RH_TO_DATE,USER_CREATE,USER_MOD,LocError,GDB_GEOMATTR_DATA",RH.LRSE_FEDERAL_AID,"OBJECTID,FEDERAL_AID_ID,ROUTE_ID,FROM_MEASURE,TO_MEASURE,FAS_TYPE,FIELD_ESTABLISH_DATE,SYSTEM_CREATE_DATE,SYSTEM_MOD_DATE,RH_FROM_DATE,RH_TO_DATE,USER_CREATE,USER_MOD,LocError,GDB_GEOMATTR_DATA",RH.LRSE_MAINT_OPERATIONS,"OBJECTID,MAINT_OPERATIONS_ID,ROUTE_ID,FROM_MEASURE,TO_MEASURE,SERVICE_ORG,SECTION_TYPE,IDENT,RTSIGN_NAME,LOCATION,COMMENTS,COMMENTS2,FIELD_ESTABLISH_DATE,SYSTEM_CREATE_DATE,SYSTEM_MOD_DATE,RH_FROM_DATE,RH_TO_DATE,USER_CREATE,USER_MOD,LocError,DISTRICT,Name,GDB_GEOMATTR_DATA",RH.LRSE_NHS,"OBJECTID,NHS_ID,ROUTE_ID,FROM_MEASURE,TO_MEASURE,NHS,NHS_APPROVED_DATE,FIELD_ESTABLISH_DATE,SYSTEM_CREATE_DATE,SYSTEM_MOD_DATE,RH_FROM_DATE,RH_TO_DATE,USER_CREATE,USER_MOD,LocError,GDB_GEOMATTR_DATA",RH.LRSE_STATE_FUNCT_CLASS,"OBJECTID,STATE_FUNCTIONAL_CLASS_ID,ROUTE_ID,FROM_MEASURE,TO_MEASURE,STATE_FUNCTIONAL_CLASS,FIELD_ESTABLISH_DATE,SYSTEM_CREATE_DATE,SYSTEM_MOD_DATE,RH_FROM_DATE,RH_TO_DATE,USER_CREATE,USER_MOD,LocError,GDB_GEOMATTR_DATA",RH.LRSE_SURFACE_TYPE,"OBJECTID,SURFACE_TYPE_ID,ROUTE_ID,FROM_MEASURE,TO_MEASURE,SURFACE_TYPE,FIELD_ESTABLISH_DATE,SYSTEM_CREATE_DATE,SYSTEM_MOD_DATE,RH_FROM_DATE,RH_TO_DATE,USER_CREATE,USER_MOD,LocError,GDB_GEOMATTR_DATA"
    ATTRS_TO_EXPOSE = FROM_MEASURE OBJECTID RH_FROM_DATE RH_TO_DATE ROUTE_ID TO_MEASURE fme_feature_type
    ATTR_ACCUM_MODE = Only Use Result
    COMBINE_GEOM = Use Initiator
    DATASET = @Value(_connSQL_RIL_LRS)
    FEATURETYPES = @Value(_pLayers)
    FORMAT = MSSQL_ADO
    MSSQL_ADO_APPLICATION_INTENT = ReadOnly
    MSSQL_ADO_NAMED_CONNECTION = @Value(_connSQL_RIL_LRS)
    OUTPUT_FEATURES_DISPLAY = Schema and Data Features
    WHERE:
      (@Value(_filter_event_by_observe_date_route_pattern))
       AND
      (@Value(_filter_event_by_observe_date_county))
    <OTHER> -> PythonCaller_2
    INITIATOR -> Tester
Tester
    BOOL_OP = OR
    TEST_CLAUSE = TEST $(pFormatOutput) IN SHAPEFILE,FILEGDB
    TEST_MODE = TEST
    PASSED -> FRD-SQL-RIL_LRS-ROUTES [INITIATOR]
Junction_2
    -> FWR-EXCEL [CSV]
Junction
    -> FWR-EXCEL [Output]
FWR-EXCEL: FeatureWriter
    DATASET = $(FME_SHAREDRESOURCE_TEMP)\$(WORKSPACE_NAME)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert

Bookmark: Overlay prep and post process
Note: Get and set value of an attribute via parameter
PythonCaller_2
    NEW_ATTRIBUTES = EventValue
    PYTHONSOURCE:
      import fme
      import fmeobjects

      def processFeature(feature):

          """ get parameter value for the columns of interest """

          myColList = FME_MacroValues['pAttributes'].split(' ')

          """ put values in an array """

          values = []

          values.append('|')

          for col in myColList:

              values.append(str(feature.getAttribute(col)))

          """ combine the column values """

          feature.setAttribute('EventValue','|'.join(values))

          """ expose the output colum """
    PYTHONSYMBOL = processFeature
    -> StringReplacer
StringReplacer
    CASE = YES
    FIND_TEXT = |None
    NO_MATCH = _FME_NO_OP_
    REGEXP = NO
    SRC_ATTRS = EventValue
    -> StringReplacer_2
StringReplacer_2
    CASE = YES
    FIND_TEXT = |
    NO_MATCH = _FME_NO_OP_
    REGEXP = NO
    SRC_ATTRS = EventValue
    -> Counter_2
Counter_2
    CNT_ATTR = _id
    DOMAIN = counter
    SCOPE = Global
    START = 0
    -> lrs_event_overlayer_2
lrs_event_overlayer_2
    EVENTVALUE = @Value(EventValue)
    FME_FEATURE_TYPE = @Value(fme_feature_type)
    FROM_MEASURE = @Value(FROM_MEASURE)
    OBJECTID = @Value(OBJECTID)
    ROUTE_ID = @Value(ROUTE_ID)
    TO_MEASURE = @Value(TO_MEASURE)
    _ID = @Value(_id)
    pCrossLayerAttrs = NAT_FUNCTIONAL_CLASS URBAN_CODE
    pLayers = $(pLayers)
    pPrim_Attr = FACILITY
    -> PythonCaller_3
Note: concate layer attributes
PythonCaller_3
    NEW_ATTRIBUTES = EventValues
    PYTHONSOURCE:
      import fme
      import fmeobjects

      def processFeature(feature):

          """ get parameter value for the columns of interest """

          myColList = FME_MacroValues['pLayers'].split(' ')

          """ put values in an array """

          values = []


          for col in myColList:

              values.append(str(feature.getAttribute(col)))

          """ combine the column values """

          feature.setAttribute('EventValues','\t'.join(values))

          """ expose the output colum """
    PYTHONSYMBOL = processFeature
    -> AttributeCreator_4
AttributeCreator_4
    ATTR_TABLE = SET_TO _result = @Value(ROUTE_ID)	@Value(FROM_MEASURE)	@Value(TO_MEASURE)	@Value(EventValues)
    -> AttributeKeeper
AttributeKeeper
    CREATE_BULK_MODE_FEATURES = NO
    KEEP_ATTRS = _result
    -> Counter
Counter
    CNT_ATTR = _seq
    DOMAIN = counter
    SCOPE = Global
    START = 1
    -> Sorter_2

Bookmark: Creating Shape file
FRD-SQL-RIL_LRS-ROUTES: FeatureReader
    ATTRIBUTES = RH.LRSN_County_Milepoint_evw,"OBJECTID,FROMDATE,TODATE,CO_CountyID,CO_SignSystem,CO_RouteNumber,CO_SubRoute,CO_SuppCode,CO_RouteDirection,CO_ExitNumber,CO_RampLetter,CO_ROUTEID,SurveyDirection,CO_RouteLabel,USER_CREATE,SYSTEM_CREATE_DATE,USER_MOD,SYSTEM_MOD_DATE,SDE_STATE_ID"
    ATTRS_TO_EXPOSE = CO_ROUTEID
    ATTR_ACCUM_MODE = Only Use Result
    COMBINE_GEOM = Use Result
    DATASET = @Value(_connSQL_RIL_LRS)
    FEATURETYPES = RH.LRSN_County_Milepoint_evw
    FORMAT = MSSQL_SPATIAL
    INTERACT = NONE
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = @Value(_connSQL_RIL_LRS)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    WHERE:
      (@Value(_filter_route_by_observe_date_route_pattern))
      AND
      (@Value(_filter_route_by_observe_date_county))
    <OTHER> -> LRS_GeoCoder [LRS_Route_Features]
Tester_3
    BOOL_OP = OR
    TEST_CLAUSE = TEST $(pFormatOutput) IN SHAPEFILE,FILEGDB
    TEST_MODE = TEST
    PASSED -> AttributeCreator_6
Note: Set fme type to fme_line
AttributeCreator_6
    ATTR_TABLE = SET_TO fme_type = fme_line
    -> FWR-SHP_FGDB [CSV]
Tester_2
    BOOL_OP = OR
    TEST_CLAUSE = TEST $(pFormatOutput) IN SHAPEFILE,FILEGDB
    TEST_MODE = TEST
    PASSED -> AttributeExposer_2
AttributeExposer_2
    ATTR_LIST = ROUTE_ID,FROM_MEASURE,TO_MEASURE
    -> LRS_GeoCoder [LRS_Events]
LRS_GeoCoder
    pEvent_F_Meas = FROM_MEASURE
    pEvent_Route_ID = ROUTE_ID
    pEvent_T_Meas = TO_MEASURE
    pLRS_Route_ID = CO_ROUTEID
    pPrecision = 3
    LRS_Event_Features -> AttributeManager
Note: Set to workspace name
AttributeManager
    ATTR_TABLE:
      REMOVE _oFMeas
      REMOVE _oTMeas
      REMOVE CO_ROUTEID
      SET_TO fme_feature_type = $(WORKSPACE_NAME)
    USER_EXPOSED_ATTRIBUTES = fme_feature_type
    -> FWR-SHP_FGDB [CSV]
FWR-SHP_FGDB: FeatureWriter
    DATASET = $(FME_SHAREDRESOURCE_TEMP)\$(WORKSPACE_NAME)
    DATASET_ATTR = _dataset
    FEATURE_TYPE_LIST_ATTR = _feature_types
    FORMAT = GENERIC
    GENERIC_DESTINATION_DATASETTYPE_VALIDATION = Yes
    GENERIC_FORMAT = $(pFormatOutput)
    GENERIC_MIME_TYPE = text/plain
    TOTAL_FEATURES_WRITTEN_ATTR = _total_features_written

Bookmark: Header Management
Creator_3
    GEOMTYPE = Geometry Object
    NUM = 1
    CREATED -> AttributeCreator_2
Note: Creatr header with tab delimited
AttributeCreator_2
    ATTR_TABLE:
      SET_TO _result = ROUTE_ID	FROM_MEASURE	TO_MEASURE	@ReplaceString(@ReplaceString($(pLayers),RH.LRSE_,,)," ", 	, caseSensitive=TRUE)
      SET_TO _seq = 0
    -> Sorter_2
Note: Put header first
Sorter_2
    SORT_PARM = _seq NATURAL ASCENDING
    SORTED -> FWR-CSV [text_line]

Bookmark: Write CSV and Excel Output
FWR-CSV: FeatureWriter
    DATASET = $(FME_SHAREDRESOURCE_TEMP)\$(WORKSPACE_NAME).txt
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> FRD-CSV [INITIATOR]
FRD-CSV: FeatureReader
    ATTRIBUTES = CSV,"ROUTE_ID,FROM_MEASURE,TO_MEASURE,AADT,ACCESS_CONTROL,ALT_ROUTE_NAME"
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = tab
    CSV2_ENCODING = windows-1252
    CSV2_ENFORCE_STRICT_SCHEMA = No
    CSV2_FEATURE_TYPE_NAME = FILE_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(_dataset)
    FORMAT = CSV2
    INTERACT = NONE
    OUTPUT_FEATURES_DISPLAY = Schema and Data Features
    <SCHEMA> -> Junction_2
    <SCHEMA> -> Tester_3
    <OTHER> -> Junction_2
    <OTHER> -> AttributeExposer
    <OTHER> -> Tester_2

Bookmark: Summarization
AttributeExposer
    ATTR_LIST = ROUTE_ID,FROM_MEASURE,TO_MEASURE
    -> AttributeCreator
AttributeCreator
    ATTR_TABLE:
      SET_TO COUNTY = @Left(@Value(ROUTE_ID),2)
      SET_TO SEG_LENGTH = @round(@Value(TO_MEASURE) - @Value(FROM_MEASURE), 3)
    -> StatisticsCalculator
StatisticsCalculator
    CALCULATION_MODE = NUMERIC
    FEAT_STATS = SEG_LENGTH,NUMERIC_MODE,,,,SUM,,,,,,,,,
    GROUP_BY = $(pSumDims)
    SUMMARY -> PythonCaller_4
Note: concate summarizing dimension values
PythonCaller_4
    NEW_ATTRIBUTES = _result
    PYTHONSOURCE:
      import fme
      import fmeobjects

      def processFeature(feature):

          """ get parameter value for the columns of interest """

          myColList = FME_MacroValues['pSumDims'].split(' ')

          """ put values in an array """

          values = []


          for col in myColList:

              print(col)

              values.append(str(feature.getAttribute(col)))

          """ combine the column values """

          feature.setAttribute('_result','\t'.join(values))

          """ expose the output colum """
    PYTHONSYMBOL = processFeature
    -> AttributeCreator_3
AttributeCreator_3
    ATTR_TABLE = SET_TO _result = @Value(_result) 	@round(@Value(SEG_LENGTH.sum),3)
    -> AttributeKeeper_3
AttributeKeeper_3
    CREATE_BULK_MODE_FEATURES = NO
    KEEP_ATTRS = _result,_seq
    -> Counter_3
Counter_3
    CNT_ATTR = _seq
    DOMAIN = counter
    SCOPE = Global
    START = 1
    -> Sorter_3
Creator_2
    GEOMTYPE = Geometry Object
    NUM = 1
    CREATED -> AttributeCreator_5
Note: Creatr header with tab delimited
AttributeCreator_5
    ATTR_TABLE:
      SET_TO _result = @ReplaceString($(pSumDims)," ", 	, caseSensitive=TRUE)	Total Length
      SET_TO _seq = 0
    -> Sorter_3
Note: Put header first
Sorter_3
    SORT_PARM = _seq NATURAL ASCENDING
    SORTED -> FWR-CSV_2 [text_line]
FWR-CSV_2: FeatureWriter
    DATASET = $(FME_SHAREDRESOURCE_TEMP)\$(WORKSPACE_NAME)_sum.txt
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> AttributeKeeper_2
AttributeKeeper_2
    CREATE_BULK_MODE_FEATURES = NO
    KEEP_ATTRS = _dataset
    -> FRD-CSV_2 [INITIATOR]
FRD-CSV_2: FeatureReader
    ATTRIBUTES = CSV,"ROUTE_ID,FROM_MEASURE,TO_MEASURE,AADT,ACCESS_CONTROL,ALT_ROUTE_NAME"
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = tab
    CSV2_ENCODING = windows-1252
    CSV2_ENFORCE_STRICT_SCHEMA = No
    CSV2_FEATURE_TYPE_NAME = FILE_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(_dataset)
    FORMAT = CSV2
    INTERACT = NONE
    OUTPUT_FEATURES_DISPLAY = Schema and Data Features
    <SCHEMA> -> Junction
    <OTHER> -> Junction

FME custom transformer lrs_event_overlayer
Takes a single stream event and conducts event overlay with raw data and gap report

Parameters:
- pLayers =
- _ID = @Value(_id)   # Id
- EVENTVALUE = @Value(EventValue)   # EventValue
- FROM_MEASURE = @Value(FROM_MEASURE)   # From Measure
- ROUTE_ID = @Value(ROUTE_ID)   # Route Id
- TO_MEASURE = @Value(TO_MEASURE)   # To Measure
- FME_FEATURE_TYPE = @Value(fme_feature_type)   # Fme Feature Type
- OBJECTID = @Value(OBJECTID)
- pPrim_Attr = FACILITY   # Attribute from Primary HPMS layer
- pCrossLayerAttrs = NAT_FUNCTIONAL_CLASS URBAN_CODE   # Attributes from cross-check layers

Input (input)
    -> InlineQuerier [Input_2]
Note: Add layer count
InlineQuerier
    QUERY_DEF:
      Ouput,WITH foo AS (SELECT DISTINCT "fme_feature_type" FROM "Input_2")
      , foo2 AS (SELECT COUNT(1) "_layer_count" FROM foo)
      SELECT "_id","fme_feature_type","FROM_MEASURE","EventValue","ROUTE_ID","TO_MEASURE", "_layer_count"
      FROM "Input_2", foo2
      ,FIRST
    QUERY_SCHEMA = Ouput,_id,integer,fme_feature_type,varchar(200),FROM_MEASURE,varchar(200),EventValue,text,ROUTE_ID,varchar(200),TO_MEASURE,varchar(200),_layer_count,
    TABLE_DEF = Input_2,FROM_MEASURE,varchar(200),ROUTE_ID,varchar(200),TO_MEASURE,varchar(200),fme_feature_type,varchar(200),OBJECTID,varchar(200),_id,integer,EventValue,text
    Ouput -> LRS_EventLineOnLine_SS [LRS_Events]
    Ouput -> FeatureJoiner [RIGHT]
LRS_EventLineOnLine_SS
    pEvent_F_Meas = FROM_MEASURE
    pEvent_ID = _id
    pEvent_Route_ID = ROUTE_ID
    pEvent_T_Meas = TO_MEASURE
    pLayer_Name = fme_feature_type
    pPrecision = 3
    -> ListExploder
ListExploder
    ATTR_ACCUM_MODE = Merge List Attributes
    ATTR_CONFLICT_RES = Use List Attribute Values
    INDEX_ATTR = _element_index
    LIST_ATTR = _oEventIds{}
    ELEMENTS -> FeatureJoiner [LEFT]
FeatureJoiner
    ATTR_CONFLICT_RES = Prefer Left
    GEOMETRY_HANDLING = Prefer Left
    JOIN_KEYS = _pEvent_ID _id AUTO
    JOIN_MODE = Inner
    JOINED -> AttributePivoter
AttributePivoter
    COLUMN_GROUP_ATTR = fme_feature_type
    GROUP_TOTALS_TAG = Total
    INCLUDE_GRAND_TOTALS = No
    PIVOT_ATTR = EventValue
    PIVOT_SUMMARY_TYPES = Min
    ROW_GROUP_ATTRS = _oFMeas _oTMeas _pEvent_Route_ID
    DATA -> AttributeRenamer
AttributeRenamer
    ATTR_TABLE:
      RENAME_SET_DEFAULT _pEvent_Route_ID > ROUTE_ID
      RENAME_SET_DEFAULT _oFMeas > FROM_MEASURE
      RENAME_SET_DEFAULT _oTMeas > TO_MEASURE
    MISSING_INPUT_ATTRS = REMOVE
    -> BulkAttributeRenamer
BulkAttributeRenamer
    ATTRCHOICE = All Attributes
    CASE_DISP = YES
    MODE_CHOICE = RENAME
    PATTERN_ACTION_DISP = REMOVESUFFIX
    REPLACE_STR = _evw
    -> Output (output)
Output (output)
Note: Hard-code exposure of all layers!
AttributeExposer [off]
    ATTR_LIST = LRSE_AADT,LRSE_ACCESS_CONTROL,LRSE_ALT_ROUTE_NAME,LRSE_AT_GRADE_OTHER,LRSE_AVG_LANE_WIDTH,LRSE_BRIDGES,LRSE_CENSUS_URBAN_CODE,LRSE_COUNTY,LRSE_CRACKING_LENGTH,LRSE_CRACKING_PERCENT,LRSE_CURVE_CLASS,LRSE_DES_TRUCK_ROUTE,LRSE_DISTRICT,LRSE_FACILITY,LRSE_FAULTING,LRSE_FEDERAL_AID,LRSE_FOREST_ROUTE,LRSE_GRADE_CLASS,LRSE_GRADE_WIDTH,LRSE_HPMS_SAMPLE,LRSE_IRI,LRSE_MAINT_OPERATIONS,LRSE_MEDIAN,LRSE_NAT_FUNCT_CLASS,LRSE_NHS,LRSE_NUMBER_SIGNALS,LRSE_ORIG_SURVEY_DIR,LRSE_OWNERSHIP,LRSE_PAVEMENT_WIDTH,LRSE_PCT_GREEN_TIME,LRSE_PCT_PASS_SIGHT,LRSE_PEAK_LANES,LRSE_PEAK_PARKING,LRSE_PSR,LRSE_REVERSE_LANE,LRSE_ROUTE_STATUS,LRSE_RURAL_MUNI,LRSE_RURAL_URBAN,LRSE_RUTTING,LRSE_SCENIC_BYWAY,LRSE_SHOULDER_TYPE_RT,LRSE_SHOULDER_WIDTH_LT,LRSE_SHOULDER_WIDTH_RT,LRSE_SIGNAL,LRSE_SPECIAL_SYSTEM,LRSE_SPEED_LIMIT,LRSE_STATE_FUNCT_CLASS,LRSE_STOP_SIGNS,LRSE_STRAHNET,LRSE_STREET_NAME_DOH,LRSE_STREET_NAME_SAMS,LRSE_STRUCTURE_TYPE,LRSE_SURFACE_TYPE,LRSE_TERRAIN_TYPE,LRSE_THROUGH_LANES,LRSE_TOLL_CHARGED,LRSE_TOLL_TYPE,LRSE_TURN_LANES_L,LRSE_TURN_LANES_R,LRSE_URBAN_CODE,LRSE_WIDENING_OBSTACLE,LRSE_WIDENING_POTENTIAL,LRSE_YEAR_LAST_IMPROV
    -> AttributeRemover
AttributeRemover [off]
    REMOVE_ATTRS = FROM_MEASURE,TO_MEASURE,_element_index,ROUTE_ID,fme_feature_type,_pEvent_ID,_layer_count,_id,EventValue
