FME workspace QC_Event_Intralayer_TOPO_Batch.fmw
Description: LRS Event Topology Check
History: 2023/04/01,Gistic,Initial release

Parameters:
- pEnv = PRD   # Select Database Environment
- pLayers = RH.LRSE_FACILITY RH.LRSE_ROUTE_STATUS
- pRouteIDSignSystem = 1
- pRouteIDPattern = 3%   # Enter Route ID Pattern
- pObserveDate =   # Pick a Date (Blank for today)
- pVersion = SDE.DEFAULT   # SDE Version ("EXECUTIVE\E029937".RCE_233341)
- pOutfileSuffix =   # Output file suffix
- FME_SHAREDRESOURCE_TEMP = \\DOTB6GISTEST1\share\QCOutput   # FME Server Temporary Resource Directory

Creator
    GEOMTYPE = Geometry Object
    NUM = 1
    CREATED -> WV_Initiator
Note: Make sure the pass the current parameters to the CT!!!
WV_Initiator
    pDOT_RouteScope = 0
    pEnv = $(pEnv)
    pObserveDate = $(pObserveDate)
    pRouteIDPattern = $(pRouteIDPattern)
    pRouteIDSignSystem = $(pRouteIDSignSystem)
    -> FRD_SDE_RIL_LRS [INITIATOR]
    -> VariableSetter_3
VariableSetter_3
    SCOPE = Global
    VALUE = @Value(_suffix_output_report)
    VARNAME = _v_suffix_output_report
    -> VariableSetter_4
VariableSetter_4
    SCOPE = Global
    VALUE = @Value(_path_qc_output)
    VARNAME = _v_path_qc_output
    -> FRD_SDE_RIL_LRS_3 [INITIATOR]
Note: Expand Json summary into tabular form
TabularSummary_2
    _ERROR_COUNT = @Value(_error_count)
    _INPUT_COUNT = @Value(_Input_count)
    _RESULT = @Value(_result)
    -> VariableRetriever_7
    -> InlineQuerier [Output]
AttributeKeeper_5
    CREATE_BULK_MODE_FEATURES = NO
    KEEP_ATTRS = _dataset
    -> Junction

Bookmark: Intralayer Topology QC by Route ID - INTERACTIVE
Note: Event generic, no geometry, with only LRS columns exposed / Notice version setting here!
FRD_SDE_RIL_LRS: FeatureReader
    ATTRIBUTES = RH.LRSE_DISTRICT,"OBJECTID,DISTRICT_ID,ROUTE_ID,FROM_MEASURE,TO_MEASURE,DISTRICT,FIELD_ESTABLISH_DATE,SYSTEM_CREATE_DATE,SYSTEM_MOD_DATE,RH_FROM_DATE,RH_TO_DATE,USER_CREATE,USER_MOD,LocError,GDB_GEOMATTR_DATA",RH.LRSE_FEDERAL_AID,"OBJECTID,FEDERAL_AID_ID,ROUTE_ID,FROM_MEASURE,TO_MEASURE,FAS_TYPE,FIELD_ESTABLISH_DATE,SYSTEM_CREATE_DATE,SYSTEM_MOD_DATE,RH_FROM_DATE,RH_TO_DATE,USER_CREATE,USER_MOD,LocError,GDB_GEOMATTR_DATA",RH.LRSE_MAINT_OPERATIONS,"OBJECTID,MAINT_OPERATIONS_ID,ROUTE_ID,FROM_MEASURE,TO_MEASURE,SERVICE_ORG,SECTION_TYPE,IDENT,RTSIGN_NAME,LOCATION,COMMENTS,COMMENTS2,FIELD_ESTABLISH_DATE,SYSTEM_CREATE_DATE,SYSTEM_MOD_DATE,RH_FROM_DATE,RH_TO_DATE,USER_CREATE,USER_MOD,LocError,DISTRICT,Name,GDB_GEOMATTR_DATA",RH.LRSE_NHS,"OBJECTID,NHS_ID,ROUTE_ID,FROM_MEASURE,TO_MEASURE,NHS,NHS_APPROVED_DATE,FIELD_ESTABLISH_DATE,SYSTEM_CREATE_DATE,SYSTEM_MOD_DATE,RH_FROM_DATE,RH_TO_DATE,USER_CREATE,USER_MOD,LocError,GDB_GEOMATTR_DATA",RH.LRSE_STATE_FUNCT_CLASS,"OBJECTID,STATE_FUNCTIONAL_CLASS_ID,ROUTE_ID,FROM_MEASURE,TO_MEASURE,STATE_FUNCTIONAL_CLASS,FIELD_ESTABLISH_DATE,SYSTEM_CREATE_DATE,SYSTEM_MOD_DATE,RH_FROM_DATE,RH_TO_DATE,USER_CREATE,USER_MOD,LocError,GDB_GEOMATTR_DATA",RH.LRSE_SURFACE_TYPE,"OBJECTID,SURFACE_TYPE_ID,ROUTE_ID,FROM_MEASURE,TO_MEASURE,SURFACE_TYPE,FIELD_ESTABLISH_DATE,SYSTEM_CREATE_DATE,SYSTEM_MOD_DATE,RH_FROM_DATE,RH_TO_DATE,USER_CREATE,USER_MOD,LocError,GDB_GEOMATTR_DATA"
    ATTRS_TO_EXPOSE = FROM_MEASURE OBJECTID RH_FROM_DATE RH_TO_DATE ROUTE_ID TO_MEASURE fme_feature_type
    ATTR_ACCUM_MODE = Only Use Result
    COMBINE_GEOM = Use Result
    FEATURETYPES = $(pLayers)
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = $(pVersion)
    GEODATABASE_SDE_VERSION_TYPE = Transactional Version
    INTERACT = NONE
    OUTPUT_FEATURES_DISPLAY = Data Features
    WHERE = @Value(_filter_event_by_observe_date_route_pattern)
    <OTHER> -> GeometryRemover
    <OTHER> -> TST-ROUTE_STATUS
    <OTHER> -> AttributeKeeper_4
GeometryRemover
    -> Tester
Note: test a particular case
Tester
    BOOL_OP = OR
    TEST_CLAUSE = TEST @Value(ROUTE_ID) IN 0530002000000,5530016000000
    TEST_MODE = TEST
    PASSED -> LRS_EventQCer_3 [LRS_Events]
    FAILED -> LRS_EventQCer_3 [LRS_Events]
AttributeKeeper_4
    CREATE_BULK_MODE_FEATURES = NO
    KEEP_ATTRS = ROUTE_ID
    -> GeometryValidator_2
Note: Route system with Geometry, Using generic port and expose CO_ROUTEID
FRD_SDE_RIL_LRS_3: FeatureReader
    ATTRIBUTES = RH.LRSN_County_Milepoint,"OBJECTID,FROMDATE,TODATE,CO_CountyID,CO_SignSystem,CO_RouteNumber,CO_SubRoute,CO_SuppCode,CO_RouteDirection,CO_ExitNumber,CO_RampLetter,CO_ROUTEID,SurveyDirection,CO_RouteLabel,SHAPE.STLength()"
    ATTRS_TO_EXPOSE = CO_ROUTEID
    ATTR_ACCUM_MODE = Only Use Result
    COMBINE_GEOM = Use Result
    FEATURETYPES = RH.LRSN_County_Milepoint
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = $(pVersion)
    GEODATABASE_SDE_VERSION_TYPE = Transactional Version
    INTERACT = NONE
    OUTPUT_FEATURES_DISPLAY = Data Features
    WHERE = @Value(_filter_route_by_observe_date_route_pattern)
    <OTHER> -> Tester_2
    <OTHER> -> LRS_GeoCoder [LRS_Route_Features]
Note: test a particular case
Tester_2
    BOOL_OP = OR
    TEST_CLAUSE = TEST @Value(CO_ROUTEID) IN 0530002000000,5530016000000
    TEST_MODE = TEST
    PASSED -> LRS_EventQCer_3 [LRS_Route_Features]
    FAILED -> LRS_EventQCer_3 [LRS_Route_Features]
Note: Update to FME Hub
LRS_EventQCer_3
    pEventGroup = fme_feature_type
    pEvent_F_Meas = FROM_MEASURE
    pEvent_ID = OBJECTID
    pEvent_Route_ID = ROUTE_ID
    pEvent_T_Meas = TO_MEASURE
    pLRS_Route_ID = CO_ROUTEID
    pMinEventLength = 10
    pPrecision = 5
    pQCRules = EXTENT GAP OVERLAP SHORTSEG
    Detail -> TSF-ERRCODE
    Summary -> TabularSummary_2
TSF-ERRCODE: TestFilter
    DEFAULT_VALUE = <UNFILTERED>
    PASSED_TEST_GROUP_OUTPUT = FIRST
    TEST_LIST = "BOOL_OP,OR,COMPOSITE_TEST,""""""1"""""",TEST_CLAUSE,TEST @Value(_oErrCode) = SSG",SSG,"BOOL_OP,OR,COMPOSITE_TEST,""""""1"""""",TEST_CLAUSE,TEST @Value(_oErrCode) = GAP",GAP,"BOOL_OP,OR,COMPOSITE_TEST,""""""1"""""",TEST_CLAUSE,TEST @Value(_oErrCode) = EXT",EXT,"BOOL_OP,OR,COMPOSITE_TEST,""""""1"""""",TEST_CLAUSE,TEST @Value(_oErrCode) = OVL",OLP
    SSG -> TST-SUPCODE
    GAP -> VariableRetriever_9
    GAP -> Tester_9
    EXT -> VariableRetriever_9
    OLP -> VariableRetriever_9
Note: Exclude events on short routes
TST-SUPCODE: Tester
    BOOL_OP = COMPOSITE
    COMPOSITE_TEST = 1 AND 2
    TEST_CLAUSE:
      TEST @Value(_oErrCode) = SSG
      TEST @Substring(@Value(_oEventRoute_ID), 9,2) = 25
    TEST_MODE = TEST
    FAILED -> VariableRetriever_9
Note: Only when Route Status is involved
Tester_9
    BOOL_OP = OR
    TEST_CLAUSE = TEST @Value(_oEventGroup) = RH.LRSE_ROUTE_STATUS
    TEST_MODE = TEST
    PASSED -> Counter

Bookmark: Route Status Concurrency by Geometry
GeometryValidator_2
    ISSUE_ATTR_NAME = _issues
    PRESETS = Custom
    REPAIR = Yes
    RULES = OGC_SIMPLE_CHECK LEGACY_OGC]No]FME_CONTROLLER_QUERY_FILE]transformers/dependencies/geometryvalidator8/OGC_SIMPLE_CHECK.fme]FME_CONTROLLER_CHOICE]OGC_SIMPLE_CHECK
    SUMMARY = Detailed
    PASSED -> LineOnLineOverlayer [LINE]
Counter
    CNT_ATTR = _count
    DOMAIN = counter
    SCOPE = Global
    START = 0
    -> FeatureMerger [REQUESTOR]
    -> LRS_GeoCoder [LRS_Events]
    -> FeatureJoiner [LEFT]
LRS_GeoCoder
    pEvent_F_Meas = _oFMeas
    pEvent_Route_ID = _oEventRoute_ID
    pEvent_T_Meas = _oTMeas
    pLRS_Route_ID = CO_ROUTEID
    pPrecision = 5
    LRS_Event_Features -> AttributeKeeper_3
AttributeKeeper_3
    CREATE_BULK_MODE_FEATURES = NO
    KEEP_ATTRS = _count,_oEventRoute_ID
    -> GeometryValidator
GeometryValidator
    ISSUE_ATTR_NAME = _issues
    PRESETS = Custom
    REPAIR = Yes
    RULES = OGC_SIMPLE_CHECK LEGACY_OGC]No]FME_CONTROLLER_QUERY_FILE]transformers/dependencies/geometryvalidator8/OGC_SIMPLE_CHECK.fme]FME_CONTROLLER_CHOICE]OGC_SIMPLE_CHECK
    SUMMARY = Detailed
    PASSED -> LineOnLineOverlayer [LINE]
LineOnLineOverlayer
    ATTRS_ACCUM_MODE = Merge Attributes
    CLEANING_TOLERANCE = Automatic
    DEAGGREGATE_INPUT = Yes
    GENERATE_LIST_DROP = YES
    LIST_ATTRS_TO_INCLUDE = ROUTE_ID _count _oEventRoute_ID
    LIST_NAME = _routes
    OV_ATTR = _overlaps
    SEPARATE_COLLINEAR_SEGMENTS = No
    LINE -> Tester_7
Tester_7
    BOOL_OP = AND
    TEST_CLAUSE:
      TEST @Value(_overlaps) > 1
      TEST _oEventRoute_ID ATTRIBUTE_HAS_A_VALUE ""
    TEST_MODE = TEST
    PASSED -> DuplicateFilter
DuplicateFilter
    INPUT_ORDERED_CHOICE = No
    KEYATTR = _count _oEventRoute_ID
    UNIQUE -> FeatureJoiner [RIGHT]
FeatureJoiner
    ATTR_CONFLICT_RES = Prefer Left
    GEOMETRY_HANDLING = Prefer Left
    JOIN_KEYS = _count _count AUTO _oEventRoute_ID _oEventRoute_ID AUTO
    JOIN_MODE = Inner
    UNJOINED_LEFT -> AttributeManager_2

Bookmark: Detect Route_Status mergability
TST-ROUTE_STATUS: Tester
    BOOL_OP = OR
    TEST_CLAUSE = TEST @Value(fme_feature_type) = RH.LRSE_ROUTE_STATUS
    TEST_MODE = TEST
    PASSED -> AttributeExposer
AttributeExposer
    ATTR_LIST = ROUTE_STATUS
    -> LRS_EventMerger [Input_Event]
LRS_EventMerger
    pEvent_Attribute = ROUTE_STATUS
    pEvent_F_Meas = FROM_MEASURE
    pEvent_ID = OBJECTID
    pEvent_Route_ID = ROUTE_ID
    pEvent_T_Meas = TO_MEASURE
    pPrecision = 5
    -> TST_MERGEABLE
TST_MERGEABLE: Tester
    BOOL_OP = OR
    TEST_CLAUSE = CASE_INSENSITIVE_TEST @Value(_oMergedEventIDs) CONTAINS ,
    TEST_MODE = CASE_INSENSITIVE_TEST
    PASSED -> AttributeManager
AttributeManager
    ATTR_TABLE = REMOVE _oEventIDs{}._pEventID
    -> VariableRetriever_2

Bookmark: Excel output
VariableRetriever_2
    SCOPE = Global
    VALUE_ATTR = suffix
    VARNAME = _v_suffix_output_report
    -> VariableRetriever_11
VariableRetriever_11
    SCOPE = Global
    VALUE_ATTR = path
    VARNAME = _v_path_qc_output
    -> FeatureHolder_3
FeatureHolder_3
    -> FWT-Excel_2 [Passed]
VariableRetriever_7
    SCOPE = Global
    VALUE_ATTR = suffix
    VARNAME = _v_suffix_output_report
    -> VariableRetriever_8
VariableRetriever_8
    SCOPE = Global
    VALUE_ATTR = path
    VARNAME = _v_path_qc_output
    -> FeatureHolder
FeatureHolder
    -> FWT-Excel_2 [Summary]
VariableRetriever_9
    SCOPE = Global
    VALUE_ATTR = suffix
    VARNAME = _v_suffix_output_report
    -> VariableRetriever_10
VariableRetriever_10
    SCOPE = Global
    VALUE_ATTR = path
    VARNAME = _v_path_qc_output
    -> FeatureHolder_2
FeatureHolder_2
    -> FWT-Excel_2 [QC_Report]
Note: report name with time stemp
FWT-Excel_2: FeatureWriter
    DATASET = @Value(path)\$(WORKSPACE_NAME)-$(pEnv)-@Value(suffix)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
    SUMMARY -> InlineQuerier [Summary]

Bookmark: Serverapp Output
InlineQuerier
    QUERY_DEF:
      Merged,SELECT "Input Count","Total Error Count", "Error Code", "Count", "_dataset"
      FROM "Output", "Summary",FIRST
    QUERY_SCHEMA = Merged,"Input Count",text,"Total Error Count",varchar(200),"Error Code",varchar(200),Count,varchar(200),_dataset,text
    TABLE_DEF = Summary,_dataset,text,_total_features_written,varchar(20),Output,"Total Error Count",varchar(200),"Input Count",text,"Error Code",varchar(200),Count,varchar(200)
    Merged -> Junction
Junction
    -> HTMLReportGenerator
    -> DuplicateFilter_3
HTMLReportGenerator
    CONTENT_LIST = HEADER TABLE
    PAGE_CONFIG = HEADER{{TEXT;Batch QC Completed Successfully;HEADER;H1;HEADER_ID;;ALIGNMENT;CENTER;COLOR;0,0,0;FME_CONTROLLER_QUERY_FILE;transformers/dependencies/html5/Header.fme;FME_CONTROLLER_CHOICE;Header}}TABLE{{STYLE;DEFAULT;TABLE;Error Code|Error Code/Count|Total/Total Error Count|Total Error/Input Count|Source Count;FME_CONTROLLER_QUERY_FILE;transformers/dependencies/html5/Table.fme;FME_CONTROLLER_CHOICE;Table}}
    TITLE = RouteBatchQCSummary
    -> FWT-HTML [HTML]
DuplicateFilter_3
    INPUT_ORDERED_CHOICE = No
    KEYATTR = _dataset
    UNIQUE -> HTMLReportGenerator_2
HTMLReportGenerator_2
    CONTENT_LIST = HEADER LIST
    PAGE_CONFIG = HEADER{{TEXT;QC Report:;HEADER;H5;HEADER_ID;;ALIGNMENT;LEFT;COLOR;0,0,0;FME_CONTROLLER_QUERY_FILE;transformers/dependencies/html5/Header.fme;FME_CONTROLLER_CHOICE;Header}}LIST{{ATTR;_dataset;STYLE;DISC;COLOR;0,0,0;BADGE;<Unused>;FME_CONTROLLER_QUERY_FILE;transformers/dependencies/html5/List.fme;FME_CONTROLLER_CHOICE;List}}
    TITLE = RouteBatchQCSummary
    -> FWT-HTML [Output]
Note: For FME App Display
FWT-HTML: FeatureWriter
    DATASET = $(FME_SHAREDRESOURCE_TEMP)\$(WORKSPACE_NAME)_Summary.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written

Bookmark: Route Status Missing Segment Report
AttributeManager_2
    ATTR_TABLE = REMOVE _oEventGroup
    -> VariableRetriever_5
VariableRetriever_5
    SCOPE = Global
    VALUE_ATTR = suffix
    VARNAME = _v_suffix_output_report
    -> VariableRetriever_14
VariableRetriever_14
    SCOPE = Global
    VALUE_ATTR = path
    VARNAME = _v_path_qc_output
    -> FWT-EXCEL [Output]
StatisticsCalculator
    CALCULATION_MODE = NUMERIC
    FEAT_STATS = _length_dominant,NUMERIC_MODE,,,,SUM,,,,,,,,,
    GROUP_BY = _count _length_gap _oEventRoute_ID
    SUMMARY -> Tester_8
    SUMMARY -> FeatureJoiner_2 [RIGHT]
FeatureJoiner_2
    ATTR_CONFLICT_RES = Prefer Left
    GEOMETRY_HANDLING = Prefer Left
    JOIN_KEYS = _count _count AUTO
    JOIN_MODE = Inner
    UNJOINED_LEFT -> AttributeManager_3
AttributeManager_3
    ATTR_TABLE:
      REMOVE _oEventGroup
      REMOVE _oErrCode
      REMOVE _oErrDesc
      REMOVE _count
      REMOVE _creation_instance
      REMOVE token_response
      REMOVE _http_status_code
      REMOVE token
    -> VariableRetriever_3
VariableRetriever_3
    SCOPE = Global
    VALUE_ATTR = suffix
    VARNAME = _v_suffix_output_report
    -> VariableRetriever_12
VariableRetriever_12
    SCOPE = Global
    VALUE_ATTR = path
    VARNAME = _v_path_qc_output
    -> FWT-EXCEL [Output00]
Tester_8
    BOOL_OP = OR
    TEST_CLAUSE = TEST @Value(_length_dominant.sum) < @Value(_length_gap)
    TEST_MODE = TEST
    PASSED -> VariableRetriever_4
VariableRetriever_4
    SCOPE = Global
    VALUE_ATTR = suffix
    VARNAME = _v_suffix_output_report
    -> VariableRetriever_13
VariableRetriever_13
    SCOPE = Global
    VALUE_ATTR = path
    VARNAME = _v_path_qc_output
    -> FWT-EXCEL [Passed]
FWT-EXCEL: FeatureWriter
    DATASET = @Value(path)\ROUTE_STATUS_GAPS-$(pEnv)-@Value(suffix).xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
    SUMMARY -> AttributeKeeper_5

Bookmark: Obtain token for Esri API calls
Creator_2
    GEOMTYPE = Geometry Object
    NUM = 1
    CREATED -> HTTPCaller
Note: Credential is hardcoded. Consider add parameters or add attributes in WV_Init
HTTPCaller
    ADDITIONAL_URL_PARAMETERS = f;pjson referer;https://gisdev.transportation.wv.gov/arcgis/rest/services
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    MULTIPARTS = username StringUpload SOURCE_EXPRESSION;GISTIC;MIME_TYPE;text/plain;FME_CONTROLLER_QUERY_FILE;transformers/dependencies/http/StringUpload.fme;FME_CONTROLLER_CHOICE;StringUpload password StringUpload SOURCE_EXPRESSION;Welcome1@2020;MIME_TYPE;text/plain;FME_CONTROLLER_QUERY_FILE;transformers/dependencies/http/StringUpload.fme;FME_CONTROLLER_CHOICE;StringUpload
    REDIRECT_AUTH = ORIGINAL_DOMAIN_ONLY
    RESPONSE_TYPE = Attribute
    SPLIT_MULTIPART_DOWNLOADS = NO
    STATUS_CODE_ATTR = _http_status_code
    TARGET_ATTR = token_response
    TARGET_ATTR_ENCODING = auto-detect
    TARGET_URL = https://gisdev.transportation.wv.gov/portal/sharing/rest/generateToken?f=pjson
    TRANSFER_TIMEOUT_LENGTH = 90
    UPLOAD_TYPE = Multipart / Form Data
    USE_COOKIES = No
    VERIFY_SSL_CERTIFICATES = Yes
    -> Tester_3
Tester_3
    BOOL_OP = OR
    TEST_CLAUSE = TEST @Value(_http_status_code) = 200
    TEST_MODE = TEST
    PASSED -> JSONExtractor
    FAILED -> Terminator
Terminator
    MESSAGE = Translation Terminated
JSONExtractor
    EXTRACT_QUERY_TABLE = token json["token"]
    JSON_DOCUMENT = @Value(token_response)
    READ_FROM_FILE = NO
    EVALUATED -> FeatureMerger [SUPPLIER]

Bookmark: Esri API to find concurrencies on Route Status
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> HTTPCaller_2
    MERGED -> FeatureJoiner_2 [LEFT]
Note: Possible to do batch with multiple locations input. Need to modify jsonfragmenter. Please ask Jinzhou if needed.
HTTPCaller_2
    ADDITIONAL_URL_PARAMETERS = locations;[{"routeId": @Value(_oEventRoute_ID),"fromMeasure": @Value(_oFMeas),"toMeasure": @Value(_oTMeas)}] token;@Value(token) f;pjson
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = response
    TARGET_ATTR_ENCODING = auto-detect
    TARGET_URL = https://gisdev.transportation.wv.gov/arcgis/rest/services/Roads_And_Highways/Transactional_LRS_STG/MapServer/exts/LRSServer/networkLayers/89/concurrencies
    TRANSFER_TIMEOUT_LENGTH = 90
    USE_COOKIES = No
    VERIFY_SSL_CERTIFICATES = Yes
    -> Tester_4
Tester_4
    BOOL_OP = OR
    TEST_CLAUSE = TEST @Value(_http_status_code) = 200
    TEST_MODE = TEST
    PASSED -> AttributeCreator_3
AttributeCreator_3
    ATTR_TABLE = SET_TO _length_gap = @double(@Value(_oTMeas) - @Value(_oFMeas))
    -> AttributeKeeper
AttributeKeeper
    CREATE_BULK_MODE_FEATURES = NO
    KEEP_ATTRS = response,_count,_length_gap,_oEventRoute_ID
    -> JSONFragmenter
JSONFragmenter
    EXPLODE_FORMAT = JSON
    EXTRACT_ATTR = Yes
    JSON_ATTR = response
    JSON_QUERY = json["locations"][0]["concurrencies"][*]
    NEW_ATTRIBUTES = routeId fromMeasure toMeasure fromDate toDate sectionId isDominant
    READ_FROM_FILE = NO
    RECURSIVE = Yes
    REJECT_EMPTY_LISTS = NO
    FRAGMENTS -> Tester_5
Tester_5
    BOOL_OP = OR
    TEST_CLAUSE = TEST @Value(isDominant) = Yes
    TEST_MODE = TEST
    PASSED -> AttributeCreator_2
AttributeCreator_2
    ATTR_TABLE = SET_TO _length_dominant = @double(@Value(toMeasure) - @Value(fromMeasure))
    -> AttributeKeeper_2
AttributeKeeper_2
    CREATE_BULK_MODE_FEATURES = NO
    KEEP_ATTRS = _count,_length_dominant,_length_gap,_oEventRoute_ID,routeId
    -> AttributeRounder
AttributeRounder
    PLACES = 5
    ROUND_TYPE = Nearest
    SRC_ATTRS = _length_dominant _length_gap
    -> StatisticsCalculator

FME custom transformer Starter
This transformer is intended to start a workspace branch without the use of the creator transformer. This will end up without additional attributes (_creation_instance) at the end of the workspace.

Creator
    GEOMTYPE = Geometry Object
    NUM = 1
    CREATED -> Output (output)
Output (output)

FME custom transformer LRS_EventQCer
Conduct Quality Check on LRS Events with following values for _oError attribute:
- Short Event 
- Overlap
- Extent - Out-of-bound measure
- Extent - Non-existing route
- Gap - Partial Coverage
- Misc - <Rejection Reason>

Parameters:
- pQCRules = EXTENT   # SEGMENT,SHORTSEG Select QC rule(s) to check
- pEvent_Route_ID =   # " " Route ID column in LRS Event
- pEvent_ID =   # " " Unique ID column in LRS Event Source
- pEvent_F_Meas =   # " " From Measure column in LRS Event
- pEvent_T_Meas =   # " " To Measure column in LRS Event
- pLRS_Route_ID =   # " " Route ID column in LRS Route System
- pEventGroup =   # "" Event Group Attribute
- pPrecision = 3   # Measure Precision
- pMinEventLength = 10   # Min. Allowable Event Length (ft)

LRS_Event2SL
    pEvent_F_Meas = _pEvent_F_Meas
    pEvent_T_Meas = _pEvent_T_Meas
    -> TSF_POINT_LINE
    Rejected -> AC_EXTENT_3
TSF_POINT_LINE: TestFilter
    DEFAULT_VALUE = Lines
    PASSED_TEST_GROUP_OUTPUT = FIRST
    TEST_LIST:
      BOOL_OP,OR,COMPOSITE_TEST,<Unused>,TEST_CLAUSE,"TEST @Value(_pEvent_F_Meas) = @Value(_pEvent_T_Meas)",Points,"BOOL_OP,AND,COMPOSITE_TEST,""""""1 AND 2"""""",TEST_CLAUSE,TEST @Value(_pEvent_F_Meas) < @Value(_pEvent_T_Meas)
      TEST @sub(@Value(_pEvent_T_Meas), @Value(_pEvent_F_Meas)) <= @mult(10, 0.0001894)",Short Lines
    Short Lines -> GRM_2
    Short Lines -> Junction_2
    Lines -> Junction_2
ARN_5: AttributeRenamer
    ATTR_TABLE:
      RENAME_SET_DEFAULT _pEvent_Route_ID > _oRoute_ID
      RENAME_SET_DEFAULT _pEvent_ID > _oEvent1_ID
      RENAME_SET_DEFAULT _pEvent_F_Meas > _oFMeas
      RENAME_SET_DEFAULT _pEvent_T_Meas > _oTMeas
    MISSING_INPUT_ATTRS = PRESERVE
    -> ARD_2
Junction
    -> Detail (output)
    -> QC_Summarizer [QC_Output]
Detail (output)
Summary (output)

Bookmark: Prepare
LRS_Events (input)
    -> AC_EVENT
AC_EVENT: AttributeCreator
    ATTR_TABLE:
      SET_TO _pEvent_F_Meas = @Value($(pEvent_F_Meas))
      SET_TO _pEvent_T_Meas = @Value($(pEvent_T_Meas))
      SET_TO _pEvent_Route_ID = @Value($(pEvent_Route_ID))
      SET_TO _pEvent_ID = @Value($(pEvent_ID))
      SET_TO _pEventGroup = @Value($(pEventGroup))
    -> AttributeKeeper_2
AttributeKeeper_2
    CREATE_BULK_MODE_FEATURES = NO
    KEEP_ATTRS = _pEvent_F_Meas,_pEvent_ID,_pEvent_Route_ID,_pEvent_T_Meas,_pEventGroup
    -> InlineQuerier [Events]
    -> FeatureMerger [REQUESTOR]
    -> QC_Summarizer [QC_Input]
LRS_Route_Features (input)
    -> AC_LRS_ROUTE
AC_LRS_ROUTE: AttributeCreator
    ATTR_TABLE = SET_TO _pLRS_Route_ID = @Value($(pLRS_Route_ID))
    -> AttributeKeeper_3
AttributeKeeper_3
    CREATE_BULK_MODE_FEATURES = NO
    KEEP_ATTRS = _pLRS_Route_ID
    -> FeatureMerger [SUPPLIER]
Note: Filter by selected route
FeatureMerger
    ATTR_ACCUM_MODE = Merge Supplier
    ATTR_CONFLICT_RES = Use Requestor
    IGNORE_NULLS = No
    JOIN_KEYS = @Value(_pEvent_Route_ID) @Value(_pLRS_Route_ID) STRING
    MERGE_TYPE = Attributes Only
    PROCESS_DUPS = NO
    REJECT_NULL_MISSING_KEYS = Yes
    SUPPLIERS_FIRST = No
    MERGED -> LRS_Event2SL
    UNMERGED_REQUESTOR -> ARN_5
    USED_SUPPLIER -> LRS_RouteMeasExtractor

Bookmark: Getting results
GRM_2: GeometryRemover
    -> AttributeRenamer
AttributeRenamer
    ATTR_TABLE:
      RENAME_SET_DEFAULT _pEvent_F_Meas > _oFMeas
      RENAME_SET_DEFAULT _pEvent_T_Meas > _oTMeas
      RENAME_SET_DEFAULT _pEvent_Route_ID > _oRoute_ID
    MISSING_INPUT_ATTRS = REMOVE
    -> SS_SHORTSEG
SS_SHORTSEG: StringSearcher
    CASE = no
    REGEXP = SHORTSEG
    STRING_TO_SEARCH = $(pQCRules)
    MATCHED -> AC_SHORTSEG
AC_SHORTSEG: AttributeCreator
    ATTR_TABLE:
      SET_TO _oError = Short event - Under 10 feet long
      SET_TO _oErrCode = SSG
      SET_TO _oErrDesc = Short Event Segment
    -> AttributeManager
AC_EXTENT_3: AttributeCreator
    ATTR_TABLE:
      SET_TO _oErrCode = MSC
      SET_TO _oErrDesc = @Value(Rejection_Reason)
    -> AttributeRenamer_2
AttributeRenamer_2
    ATTR_TABLE = RENAME_SET_DEFAULT _pEvent_Route_ID > _oRoute_ID
    MISSING_INPUT_ATTRS = REMOVE
    -> AttributeManager
ARD_MEAS_2: AttributeRounder
    PLACES = $(pPrecision)
    ROUND_TYPE = Nearest
    SRC_ATTRS = _oTMeas _oFMeas
    -> TST_TOLERANCE
TST_TOLERANCE: Tester
    BOOL_OP = OR
    TEST_CLAUSE = TEST @Value(_oTMeas) > @Value(_oFMeas)
    TEST_MODE = TEST
    PASSED -> ARN_4
ARN_4: AttributeRenamer
    ATTR_TABLE:
      RENAME_SET_DEFAULT _pEvent_Route_ID > _oRoute_ID
      RENAME_SET_DEFAULT _pEvent1_ID > _oEvent1_ID
      RENAME_SET_DEFAULT _pEvent2_ID > _oEvent2_ID
    MISSING_INPUT_ATTRS = PRESERVE
    -> TF_ERR
TF_ERR: TestFilter
    DEFAULT_VALUE = Gap
    PASSED_TEST_GROUP_OUTPUT = FIRST
    TEST_LIST:
      BOOL_OP,AND,COMPOSITE_TEST,<Unused>,TEST_CLAUSE,"TEST @Value(_oEvent1_ID) ATTRIBUTE_HAS_VALUE """"
      TEST @Value(_oEvent2_ID) ATTRIBUTE_HAS_VALUE """"",Overlap,BOOL_OP,AND,COMPOSITE_TEST,<Unused>,TEST_CLAUSE,"TEST @Value(_oEvent1_ID) ATTRIBUTE_HAS_VALUE """"
      TEST @Value(_oEvent2_ID) NOT_ATTRIBUTE_HAS_VALUE """"",Extent
    Overlap -> SS_OVERLAP_2
    Extent -> SS_EXTENT_3
    Gap -> SS_GAP_3
SS_OVERLAP_2: StringSearcher
    CASE = no
    REGEXP = OVERLAP
    STRING_TO_SEARCH = $(pQCRules)
    MATCHED -> AC_OVERLAP
AC_OVERLAP: AttributeCreator
    ATTR_TABLE:
      SET_TO _oError = Overlap
      SET_TO _oErrCode = OLP
      SET_TO _oErrDesc = Overlapping Events
    -> AttributeManager
SS_EXTENT_3: StringSearcher
    CASE = no
    REGEXP = EXTENT
    STRING_TO_SEARCH = $(pQCRules)
    MATCHED -> AC_EXTENT
AC_EXTENT: AttributeCreator
    ATTR_TABLE:
      SET_TO _oError = Extent - Out-of-bound measure
      SET_TO _oErrCode = EXT
      SET_TO _oErrDesc = Event Measure Beyond Route Extent
    -> AttributeManager
Note: Identify neighbors
SS_GAP_3: StringSearcher
    CASE = no
    REGEXP = GAP
    STRING_TO_SEARCH = $(pQCRules)
    MATCHED -> InlineQuerier [GAP]
InlineQuerier
    QUERY_DEF:
      Neighbors,SELECT E."_pEvent_ID",
              G."_pEventGroup",
              G."_oRoute_ID",
              G."_oFMeas",
              G."_oTMeas"
      FROM "GAP" G LEFT JOIN "Events" E ON
              coalesce(E."_pEventGroup", 1) = coalesce(G."_pEventGroup", 1)
          AND E."_pEvent_Route_ID" = G."_oRoute_ID"
          AND (E."_pEvent_F_Meas" IN (G."_oFMeas", G."_oTMeas")  OR
                E."_pEvent_T_Meas" IN (G."_oFMeas", G."_oTMeas"))
      ,FIRST
    QUERY_SCHEMA = Neighbors,_pEvent_ID,varchar(200),_pEventGroup,varchar(200),_oRoute_ID,varchar(200),_oFMeas,varchar(20),_oTMeas,varchar(20)
    TABLE_DEF = Events,_pEvent_F_Meas,varchar(20),_pEvent_T_Meas,varchar(20),_pEvent_Route_ID,varchar(200),_pEvent_ID,varchar(200),_pEventGroup,varchar(200),GAP,_oRoute_ID,varchar(200),_oEvent1_ID,varchar(200),_oFMeas,varchar(20),_oTMeas,varchar(20),_pEventGroup,varchar(200)
    Neighbors -> Aggregator
Aggregator
    ACCUM_ATTRS_NAME = Use Attributes From One Feature
    AGGREGATE_TYPE = Homogeneous Collection (If Possible)
    GROUP_BY = _oFMeas _oRoute_ID _oTMeas _pEventGroup
    LIST_ATTRS_TO_INCLUDE = _pEvent_ID
    LIST_NAME = _EventIDs
    MODE = Geometry - Assemble One Level
    SEP = ,
    AGGREGATE -> AC_GAP
AC_GAP: AttributeCreator
    ATTR_TABLE:
      SET_TO _oError = Gap - Partial Coverage
      SET_TO _oEvent1_ID = @Value(_EventIDs{0}._pEvent_ID)
      SET_TO _oEvent2_ID = @Value(_EventIDs{1}._pEvent_ID)
      SET_TO _oErrCode = GAP
      SET_TO _oErrDesc = Partial Route Coverage
    -> AttributeRemover
AttributeRemover
    LIST_ATTRS = _EventIDs{}
    REMOVE_ATTRS = _pEvent_ID
    -> AttributeManager
ARD_2: AttributeRounder
    PLACES = $(pPrecision)
    ROUND_TYPE = Nearest
    SRC_ATTRS = _oTMeas _oFMeas
    -> SS_EXTENT_4
Note: Events having routes not included / in the route system
SS_EXTENT_4: StringSearcher
    CASE = no
    REGEXP = EXTENT
    STRING_TO_SEARCH = $(pQCRules)
    MATCHED -> AC_EXTENT_2
AC_EXTENT_2: AttributeCreator
    ATTR_TABLE:
      SET_TO _oError = Extent - None-existing route
      SET_TO _oErrCode = NRT
      SET_TO _oErrDesc = No Matching Route
    -> AttributeManager
AttributeManager
    ATTR_TABLE:
      RENAME_SET_VALUE _pEventGroup > _oEventGroup
      RENAME_SET_VALUE _oRoute_ID > _oEventRoute_ID
      REMOVE Rejection_Reason
      REMOVE _pEvent_F_Meas
      REMOVE _pEvent_T_Meas
      REMOVE _pEvent_ID
      REMOVE _pLRS_Route_ID
    -> Junction
QC_Summarizer
    _pErrCode = @Value(_oErrCode)
    pInputCol = _pEvent_ID
    Summary_output -> Summary (output)

Bookmark: Overlap
Junction_2
    -> LOLO_OVERLAP [LINE]
    -> AKP-EVENTGROUP
LOLO_OVERLAP: LineOnLineOverlayer
    ATTRS_ACCUM_MODE = Merge Attributes
    CLEANING_TOLERANCE = Automatic
    DEAGGREGATE_INPUT = Yes
    GENERATE_LIST_DROP = NO
    GROUP_BY = _pEvent_Route_ID _pEventGroup
    INCOMING_PREFIX = _o
    OV_ATTR = _overlaps
    SEPARATE_COLLINEAR_SEGMENTS = Yes
    LINE -> TS_OVERLAP
    LINE -> LineCombiner
LineCombiner
    ACCUM_ATTRS_NAME = Use Attributes From One Feature
    BREAK = no
    BREAK_CONNECTION_ATTRIBUTES = _pEvent_Route_ID _pEventGroup
    CONNECT_Z_MODE = First Wins
    CONSIDER_NODE_ELEVATION = no
    DEAGGREGATE_GEOMETRY = Deaggregate
    JUNCTIONS_IGNORE_ATTRIBUTES = Yes
    LINES_AS_SEGMENTS = No
    PRESERVE = no
    TOPOLOGY = End noded
    LINE -> AttributeKeeper
AttributeKeeper
    CREATE_BULK_MODE_FEATURES = NO
    KEEP_ATTRS = _pEvent_Route_ID,_pEventGroup
    -> CE_FMEAS_2
CE_FMEAS_2: CoordinateExtractor
    IND = 0
    MODE = Specify Coordinate
    X_ATTR = _oFMeas
    Z_DEFAULT = -9999
    -> CE_TMEAS_2
CE_TMEAS_2: CoordinateExtractor
    IND = -1
    MODE = Specify Coordinate
    X_ATTR = _oTMeas
    Z_DEFAULT = -9999
    -> GR_SL_2
GR_SL_2: GeometryRemover
    -> Counter_3
Counter_3
    CNT_ATTR = _oUID
    DOMAIN = counter
    SCOPE = Global
    START = 0
    -> LRS_EventLineOnLine [LRS_Event_Left]
TS_OVERLAP: Tester
    BOOL_OP = COMPOSITE
    COMPOSITE_TEST = 1 AND 2
    TEST_CLAUSE:
      TEST @Value(_overlaps) > 1
      TEST @Value(_pEvent_ID) < @Value(_o_pEvent_ID)
    TEST_MODE = TEST
    PASSED -> ARM_3
ARM_3: AttributeRemover
    REMOVE_ATTRS = _o_pLRS_Route_ID,_overlaps,_pEvent_T_Meas,_pEvent_F_Meas,_o_pEvent_T_Meas,_pLRS_Route_ID,_o_pEvent_F_Meas,_o_pEvent_Route_ID,_o_pEventGroup
    -> ARN
ARN: AttributeRenamer
    ATTR_TABLE:
      RENAME_SET_DEFAULT _pEvent_ID > _pEvent1_ID
      RENAME_SET_DEFAULT _o_pEvent_ID > _pEvent2_ID
    MISSING_INPUT_ATTRS = PRESERVE
    -> CE_FMEAS
CE_FMEAS: CoordinateExtractor
    IND = 0
    MODE = Specify Coordinate
    X_ATTR = _oFMeas
    Z_DEFAULT = -9999
    -> CE_TMEAS
CE_TMEAS: CoordinateExtractor
    IND = -1
    MODE = Specify Coordinate
    X_ATTR = _oTMeas
    Z_DEFAULT = -9999
    -> GR_SL
GR_SL: GeometryRemover
    -> ARD_MEAS_2
AKP-EVENTGROUP: AttributeKeeper
    CREATE_BULK_MODE_FEATURES = NO
    KEEP_ATTRS = _pEventGroup
    -> DFT-EVENTGROUP
DFT-EVENTGROUP: DuplicateFilter
    INPUT_ORDERED_CHOICE = No
    KEYATTR = _pEventGroup
    UNIQUE -> ILQ-RTE-EVENT [EventGroup]

Bookmark: Route Prep
LRS_RouteMeasExtractor
    pNodeXY = No
    pPrecision = 5
    -> GRM
GRM: GeometryRemover
    -> AK
AK: AttributeKeeper
    CREATE_BULK_MODE_FEATURES = No
    KEEP_ATTRS = _oEndMeas,_pLRS_Route_ID,_oBegMeas
    -> AttributeRounder
AttributeRounder
    PLACES = $(pPrecision)
    ROUND_TYPE = Nearest
    SRC_ATTRS = _oBegMeas _oEndMeas
    -> StringReplacer_5
StringReplacer_5
    CASE = NO
    FIND_TEXT = ^-0$
    NO_MATCH = _FME_NO_OP_
    REGEXP = YES
    REPLACE_TEXT = 0
    SRC_ATTRS = _oBegMeas,_oEndMeas
    -> ILQ-RTE-EVENT [Routes]
Note: Use SQL cartesian join to create stream with Events
ILQ-RTE-EVENT: InlineQuerier
    QUERY_DEF:
      RoutesWEventGroup,SELECT "_pEventGroup","_pLRS_Route_ID","_oBegMeas","_oEndMeas"
      FROM "EventGroup", "Routes",FIRST
    QUERY_SCHEMA = RoutesWEventGroup,_pEventGroup,varchar(200),_pLRS_Route_ID,varchar(200),_oBegMeas,float,_oEndMeas,float
    TABLE_DEF = EventGroup,_pEventGroup,varchar(200),Routes,_oBegMeas,float,_oEndMeas,float,_pLRS_Route_ID,varchar(200)
    RoutesWEventGroup -> Counter

Bookmark: Extent and Gap test
Counter
    CNT_ATTR = _oUID
    DOMAIN = counter
    SCOPE = Global
    START = 0
    -> LRS_EventLineOnLine [LRS_Event_Right]
LRS_EventLineOnLine
    pEvent1_F_Meas = _oFMeas
    pEvent1_ID = _oUID
    pEvent1_Route_ID = _pEvent_Route_ID
    pEvent1_T_Meas = _oTMeas
    pEvent2_F_Meas = _oBegMeas
    pEvent2_ID = _oUID
    pEvent2_Route_ID = _pLRS_Route_ID
    pEvent2_T_Meas = _oEndMeas
    pEventGroup = _pEventGroup
    pPrecision = 5
    UnjoinedLeft -> ARD_MEAS_2
    UnjoinedRight -> ARD_MEAS_2

FME custom transformer TabularSummary
Expand the summary QC in json to tabular form

Parameters:
- _ERROR_COUNT = @Value(_error_count)   # Error Count
- _INPUT_COUNT = @Value(_Input_count)   # Input Count
- _RESULT = @Value(_result)   # Result

Input (input)
    -> JSONFragmenter
JSONFragmenter
    EXPLODE_FORMAT = JSON
    EXTRACT_ATTR = No
    JSON_ATTR = _result
    JSON_QUERY = json["result"]
    READ_FROM_FILE = NO
    REJECT_EMPTY_LISTS = YES
    FRAGMENTS -> TST-ERR
TST-ERR: Tester
    BOOL_OP = OR
    TEST_CLAUSE = TEST @Value(_error_count) > 0
    TEST_MODE = TEST
    PASSED -> JSONFragmenter_2
    FAILED -> AttributeManager_2
JSONFragmenter_2
    EXPLODE_FORMAT = JSON
    EXTRACT_ATTR = No
    JSON_ATTR = _result
    JSON_QUERY = json[*]
    READ_FROM_FILE = NO
    REJECT_EMPTY_LISTS = YES
    FRAGMENTS -> JSONFlattener
JSONFlattener
    ERROR_LIST_ATTR = _json_error
    JSON_DOCUMENT = @Value(_result)
    READ_FROM_FILE = NO
    RECURSIVE = Yes
    -> AttributeExposer
AttributeExposer
    ATTR_LIST = _oErrCode,_oErrCode.total_count
    -> AttributeManager_3
AttributeManager_3
    ATTR_TABLE:
      REMOVE _result
      RENAME_SET_VALUE _error_count > Total Error Count
      RENAME_SET_VALUE _Input_count > Input Count
      REMOVE json_type
      REMOVE json_index
      RENAME_SET_VALUE _oErrCode > Error Code
      RENAME_SET_VALUE _oErrCode.total_count > Count
    USER_EXPOSED_ATTRIBUTES = _oRouteID.total_count
    -> Output (output)
AttributeManager_2
    ATTR_TABLE:
      REMOVE _result
      RENAME_SET_VALUE _error_count > Total Error Count
      RENAME_SET_VALUE _Input_count > Input Count
      REMOVE json_type
      REMOVE json_index
    -> Output (output)
Output (output)
