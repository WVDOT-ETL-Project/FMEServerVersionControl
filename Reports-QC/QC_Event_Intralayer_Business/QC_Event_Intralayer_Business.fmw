FME workspace QC_Event_Intralayer_Business.fmw
Title: WV_ETL_General
Description: LRS Event Business Logic Check
History: 2023/04/01,Gistic,Initial release

Parameters:
- pRule_ID = 41 42
- pEnv = PRD   # Select Database Environment
- pRouteIDSignSystem =
- pRouteIDPattern = 3%   # Enter Route ID Pattern (see instruction below)
- pVersion = SDE.DEFAULT   # SDE Version ("EXECUTIVE\E029937".RCE_233341)
- pObserveDate =   # Observation Date (Blank for today)
- pPathOutput = \\dotb6gistest1\share\QCOutput\   # Disk file output path
- pOutfileSuffix =   # Output file suffix
- FME_SHAREDRESOURCE_TEMP = \\dotb6gistest1\share\QCOutput   # FME Server Temporary Resource Directory

Creator
    GEOMTYPE = Geometry Object
    NUM = 1
    CREATED -> WV_Initiator
WV_Initiator
    pDOT_RouteScope = 0
    pEnv = $(pEnv)
    pOutfileSuffix = $(pOutfileSuffix)
    pRouteIDPattern = $(pRouteIDPattern)
    pRouteIDSignSystem = $(pRouteIDSignSystem)
    -> VariableSetter
AttributeKeeper_6
    CREATE_BULK_MODE_FEATURES = NO
    KEEP_ATTRS = _connSQL_DataMart,_connSQL_RIL_LRS,_filter_event_by_observe_date_route_pattern,_suffix_output_report
    -> FTR_SQL_DATA_MART [INITIATOR]
Note: Import rule id to pRule_ID
Note: Read rule from rule_table
FTR_SQL_DATA_MART: FeatureReader
    ATTRIBUTES = dbo.View_Rule,"rule_type,imp_type,rule_id,desc,layer,attrs,WhereClause,sql"
    ATTR_ACCUM_MODE = Merge Initiator and Result
    ATTR_CONFLICT_RES = Use Result
    ATTR_IGNORE_NULLS = No
    COMBINE_GEOM = Use Result
    DATASET = @Value(_connSQL_DataMart)
    FEATURETYPES = dbo.View_Rule
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(_connSQL_DataMart)
    MSSQL_ADO_QUERY_FEATURE_TYPES_FOR_MERGE_FILTERS = Yes
    MSSQL_ADO_READ_CACHE_SIZE = 10
    OUTPUT_FEATURES_DISPLAY = Schema and Data Features
    WHERE:
      rule_id IN (
      @ReplaceRegularExpression($(pRule_ID),[\s+],",",caseSensitive=TRUE)
      )
    dbo.View_Rule -> AttributeManager_4
Note: Remove '_evw' if it is a view
AttributeManager_4
    ATTR_TABLE:
      SET_TO layer = FME_CONDITIONAL:DEFAULT_VALUE'@Value(layer)'BOOL_OP;OR;COMPOSITE_TEST;1;CASE_SENSITIVE_TEST @Value(layer) CONTAINS_REGEX .*evw(i)?.*'@TrimRight(@Value(layer),_evw)'FME_NUM_CONDITIONS2___
      RENAME_SET_VALUE sql = FME_CONDITIONAL:DEFAULT_VALUE'@Value(sql)'BOOL_OP;OR;COMPOSITE_TEST;1;CASE_SENSITIVE_TEST @Value(sql) CONTAINS_REGEX .*View(i)?.*'@ReplaceString(@Value(sql),_evw , ,caseSensitive=TRUE)'FME_NUM_CONDITIONS2___
    -> AttributeCreator_2
AttributeCreator_2
    ATTR_TABLE = SET_TO sql = @Value(sql) AND @Value(_filter_event_by_observe_date_route_pattern)
    -> AttributeKeeper_4
AttributeKeeper_4
    CREATE_BULK_MODE_FEATURES = NO
    KEEP_ATTRS = _connSQL_RIL_LRS,layer,rule_id,sql,rule_type,_path_report_output,_suffix_output_report
    -> SQL_RIL_LRS [INITIATOR]
Note: Execute Rule SQL
SQL_RIL_LRS: SQLExecutor
    ATTR_IGNORE_NULLS = No
    COMBINE_ATTRS = Keep Result Attributes if Conflict
    COMBINE_GEOM = Initiator Geometry Only
    DATASET = @Value(_connSQL_RIL_LRS)
    EXPOSED_ATTRIBUTE_LIST = ROUTE_ID,OBJECTID,layer
    FORMAT = MSSQL_SPATIAL
    MSSQL_SPATIAL_APPLICATION_INTENT = ReadWrite
    MSSQL_SPATIAL_COMMAND_TIMEOUT = 30
    MSSQL_SPATIAL_CREATE_FEATURE_TABLES_FROM_DATA = Yes
    MSSQL_SPATIAL_NAMED_CONNECTION = @Value(_connSQL_RIL_LRS)
    MSSQL_SPATIAL_QUERY_FEATURE_TYPES_FOR_MERGE_FILTERS = Yes
    OUTPUT_FEATURES_DISPLAY = Schema and Data Features
    SQL_STATEMENT:
      EXEC sde.set_current_version '$(pVersion)';
      @Value(sql)
    RESULT -> VariableRetriever
    INITIATOR -> VariableRetriever_4

Bookmark: Save path and suffix to variables
VariableSetter
    SCOPE = Global
    VALUE = @Value(_suffix_output_report)
    VARNAME = _v_suffix_output_report
    -> VariableSetter_2
VariableSetter_2
    SCOPE = Global
    VALUE = @Value(_path_qc_output)
    VARNAME = _v_path_qc_output
    -> AttributeKeeper_6

Bookmark: REstore vars to attributes
VariableRetriever
    SCOPE = Global
    VALUE_ATTR = suffix
    VARNAME = _v_suffix_output_report
    -> VariableRetriever_3
VariableRetriever_3
    SCOPE = Global
    VALUE_ATTR = path
    VARNAME = _v_path_qc_output
    -> AttributeManager
VariableRetriever_4
    SCOPE = Global
    VALUE_ATTR = suffix
    VARNAME = _v_suffix_output_report
    -> VariableRetriever_5
VariableRetriever_5
    SCOPE = Global
    VALUE_ATTR = path
    VARNAME = _v_path_qc_output
    -> AttributeManager_2

Bookmark: Excel output
Note: Detail
AttributeManager
    ATTR_TABLE:
      REMOVE sql
      REMOVE _connSQL_RIL_LRS
      RENAME_SET_VALUE rule_id > RULE_ID
      RENAME_SET_VALUE layer > LAYER_NAME
    -> FWT-Excel [QC_Report]
Note: Summary
AttributeManager_2
    ATTR_TABLE:
      RENAME_SET_VALUE rule_id > RULE_ID
      SET_TO _oErrCode = @Value(rule_type)
      SET_TO _oErrDesc = Violating @Value(rule_type) Rule: @Value(RULE_ID)
      RENAME_SET_VALUE layer > LAYER_NAME
      REMOVE sql
      REMOVE _connSQL_RIL_LRS
      RENAME_SET_VALUE _matched_records > Count
      REMOVE rule_type
    -> InlineQuerier [Output]
    -> FWT-Excel [Summary]
Note: report name with time stemp
FWT-Excel: FeatureWriter
    DATASET = $(pPathOutput)\$(WORKSPACE_NAME)-$(pEnv)-@Value(_suffix_output_report)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
    SUMMARY -> InlineQuerier [Summary]

Bookmark: For Server app display
InlineQuerier
    QUERY_DEF:
      Merged,SELECT "_oErrCode","_oErrDesc","RULE_ID","LAYER_NAME","Count", "_dataset"
      FROM "Output", "Summary",FIRST
    QUERY_SCHEMA = Merged,_oErrCode,varchar(200),_oErrDesc,varchar(200),RULE_ID,text,LAYER_NAME,text,Count,integer,_dataset,text
    TABLE_DEF = Summary,_dataset,text,_total_features_written,varchar(20),Output,RULE_ID,text,_oErrCode,varchar(200),_oErrDesc,varchar(200),LAYER_NAME,text,Count,integer
    Merged -> HTMLReportGenerator
HTMLReportGenerator
    CONTENT_LIST = HEADER TABLE HEADER
    PAGE_CONFIG = HEADER{{TEXT;Batch QC Completed Successfully;HEADER;H1;HEADER_ID;;ALIGNMENT;CENTER;COLOR;0,0,0;FME_CONTROLLER_QUERY_FILE;transformers/dependencies/html5/Header.fme;FME_CONTROLLER_CHOICE;Header}}TABLE{{STYLE;DEFAULT;TABLE;_oErrCode|Error Code/RULE_ID|Rule ID/LAYER_NAME|Event Layer/Count|Total;FME_CONTROLLER_QUERY_FILE;transformers/dependencies/html5/Table.fme;FME_CONTROLLER_CHOICE;Table}}HEADER{{TEXT;QC Report:  @Value(_dataset).xlsx;HEADER;H5;HEADER_ID;;ALIGNMENT;LEFT;COLOR;0,0,0;FME_CONTROLLER_QUERY_FILE;transformers/dependencies/html5/Header.fme;FME_CONTROLLER_CHOICE;Header}}
    TITLE = RouteBatchQCSummary
    -> FWT-HTML [HTML]
Note: For FME App Display
FWT-HTML: FeatureWriter
    DATASET = $(FME_SHAREDRESOURCE_TEMP)\$(WORKSPACE_NAME)_Summary.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written
