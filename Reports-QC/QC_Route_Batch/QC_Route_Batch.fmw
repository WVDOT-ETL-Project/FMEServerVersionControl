FME workspace QC_Route_Batch.fmw
Title: WV_ETL_General
Description: LRS Route Check
History: 2023/04/01,Gistic,Initial release,2023/04/28,BG,Expose System_Mod_Date

Parameters:
- pEnv = PRD   # Select Database Environment
- pRouteIDSignSystem = 1
- pRouteIDPattern = %   # Enter Route ID Pattern
- pVersion = SDE.DEFAULT   # Enter Version (such as "EXECUTIVE\E029937".RCE_233341)
- pObserveDate =   # Pick a Date (Blank for today)
- pOutfileSuffix =   # Output file suffix
- FME_SHAREDRESOURCE_TEMP = \\DOTB6GISTEST1\share\QCOutput   # FME Server Temporary Resource Directory

Creator
    GEOMTYPE = Geometry Object
    NUM = 1
    CREATED -> WV_Initiator
WV_Initiator
    pDOT_RouteScope = 0
    pEnv = $(pEnv)
    pObserveDate = $(pObserveDate)
    pOutfileSuffix = $(pOutfileSuffix)
    pRouteIDPattern = $(pRouteIDPattern)
    pRouteIDSignSystem = $(pRouteIDSignSystem)
    pRouteIDs = " "
    -> VariableSetter_2
VariableSetter_2
    SCOPE = Global
    VALUE = @Value(_suffix_output_report)
    VARNAME = _v_suffix_output_report
    -> VariableSetter_3
VariableSetter_3
    SCOPE = Global
    VALUE = @Value(_path_qc_output)
    VARNAME = _v_path_qc_output
    -> FRD_PRD_SDE_RIL_LRS [INITIATOR]
Note: Use the batch filter
Note: VariableRetriever_2
FRD_PRD_SDE_RIL_LRS: FeatureReader
    ATTRS_TO_EXPOSE = CO_ROUTEID SYSTEM_MOD_DATE
    ATTR_ACCUM_MODE = Only Use Result
    COMBINE_GEOM = Use Result
    FEATURETYPES = RH.LRSN_County_Milepoint
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = $(pVersion)
    GEODATABASE_SDE_VERSION_TYPE = Transactional Version
    INTERACT = NONE
    OUTPUT_FEATURES_DISPLAY = Data Features
    WHERE = @Value(_filter_route_by_observe_date_route_pattern)
    <OTHER> -> LRS_RouteQCer [LRS_Route_System]
    <OTHER> -> FeatureJoiner_2 [RIGHT]
    INITIATOR -> FRD_SDE_RIL_LRS_2 [INITIATOR]
Note: this is to use the linked version when upgradted to 2022.2.2!
LRS_RouteQCer: LRS_RouteQCer_edit
    pLRS_Route_ID = CO_ROUTEID
    pMinSegLength = 2
    pNumNetworks = 1
    pPrecisionCS = 6
    pPrecisionMeas = 3
    pQCRules = MON SGS SPK USH
    pSpikeAngle = 25
    QC_Report -> AttributeManager
    QC_Report -> FeatureJoiner [LEFT]
    Summary -> TabularSummary_2

Bookmark: Serverapp Output
Note: Expand Json summary into tabular form
TabularSummary_2
    _ERROR_COUNT = @Value(_error_count)
    _INPUT_COUNT = @Value(_Input_count)
    _RESULT = @Value(_result)
    -> VariableRetriever_3
    -> InlineQuerier [Output]
InlineQuerier
    QUERY_DEF:
      Merged,SELECT "Input Count","Total Error Count", "Error Code", "Count", "_dataset"
      FROM "Output", "Summary",FIRST
    QUERY_SCHEMA = Merged,"Input Count",text,"Total Error Count",varchar(200),"Error Code",varchar(200),Count,varchar(200),_dataset,text
    TABLE_DEF = Summary,_dataset,text,_total_features_written,varchar(20),Output,"Total Error Count",varchar(200),"Input Count",text,"Error Code",varchar(200),Count,varchar(200)
    Merged -> HTMLReportGenerator
HTMLReportGenerator
    CONTENT_LIST = HEADER TABLE HEADER
    PAGE_CONFIG = HEADER{{TEXT;Batch QC Completed Successfully;HEADER;H1;HEADER_ID;;ALIGNMENT;CENTER;COLOR;0,0,0;FME_CONTROLLER_QUERY_FILE;transformers/dependencies/html5/Header.fme;FME_CONTROLLER_CHOICE;Header}}TABLE{{STYLE;DEFAULT;TABLE;Error Code|Error Code/Count|Total/Total Error Count|Total Error/Input Count|Source Count;FME_CONTROLLER_QUERY_FILE;transformers/dependencies/html5/Table.fme;FME_CONTROLLER_CHOICE;Table}}HEADER{{TEXT;QC Report:  @Value(_dataset).xlsx;HEADER;H5;HEADER_ID;;ALIGNMENT;LEFT;COLOR;0,0,0;FME_CONTROLLER_QUERY_FILE;transformers/dependencies/html5/Header.fme;FME_CONTROLLER_CHOICE;Header}}
    TITLE = RouteBatchQCSummary
    -> FWT-HTML [HTML]
Note: For FME App Display
FWT-HTML: FeatureWriter
    DATASET = $(FME_SHAREDRESOURCE_TEMP)\$(WORKSPACE_NAME)_Summary.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written

Bookmark: Excel output
VariableRetriever_3
    SCOPE = Global
    VALUE_ATTR = path
    VARNAME = _v_path_qc_output
    -> VariableRetriever_2
VariableRetriever_2
    SCOPE = Global
    VALUE_ATTR = suffix
    VARNAME = _v_suffix_output_report
    -> FWT-Excel_2 [Summary]
AttributeManager
    ATTR_TABLE:
      RENAME_SET_VALUE _oRouteID > ROUTE_ID
      RENAME_SET_VALUE _oErrCode > ERROR_CODE
      RENAME_SET_VALUE _oErrDesc > DESCRIPTION
      RENAME_SET_VALUE _oLength > LENGTH
      RENAME_SET_VALUE _oMeasure1 > MEASURE_1
      RENAME_SET_VALUE _oMeasure2 > MEASURE_2
      RENAME_SET_VALUE _oNetworkID > NETWORK_ID
    -> FeatureJoiner_2 [LEFT]
FeatureJoiner_2
    ATTR_CONFLICT_RES = Prefer Left
    GEOMETRY_HANDLING = Prefer Left
    JOIN_KEYS = ROUTE_ID CO_ROUTEID AUTO
    JOIN_MODE = Inner
    JOINED -> AttributeCreator
Note: Preserve leading 0's
AttributeCreator
    ATTR_TABLE = SET_TO ROUTE_ID = '@Value(ROUTE_ID)
    -> VariableRetriever_6
VariableRetriever_6
    SCOPE = Global
    VALUE_ATTR = suffix
    VARNAME = _v_suffix_output_report
    -> VariableRetriever_7
VariableRetriever_7
    SCOPE = Global
    VALUE_ATTR = path
    VARNAME = _v_path_qc_output
    -> FWT-Excel_2 [QC_Report]
Note: report name with time stemp
FWT-Excel_2: FeatureWriter
    DATASET = @Value(path)\$(WORKSPACE_NAME)-$(pEnv)-@Value(suffix)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
    SUMMARY -> InlineQuerier [Summary]

Bookmark: Special Alpha route exclusion
Note: Alpha Exclusion
FRD_SDE_RIL_LRS_2: FeatureReader
    ATTRIBUTES = RH.Alpha_Route_Gaps,"OBJECTID,RouteID,Comment,Measure"
    ATTR_ACCUM_MODE = Only Use Result
    COMBINE_GEOM = Use Result
    FEATURETYPES = RH.Alpha_Route_Gaps
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = $(pVersion)
    GEODATABASE_SDE_VERSION_TYPE = Transactional Version
    INTERACT = NONE
    OUTPUT_FEATURES_DISPLAY = Data Features
    RH.Alpha_Route_Gaps -> AttributeKeeper
AttributeKeeper
    CREATE_BULK_MODE_FEATURES = NO
    KEEP_ATTRS = Measure,RouteID,_path_report_output,_report_name_root,_report_name_timestamp
    -> FeatureJoiner [RIGHT]
Note: Alpha Exclusion
FeatureJoiner
    ATTR_CONFLICT_RES = Prefer Left
    GEOMETRY_HANDLING = Prefer Left
    JOIN_KEYS = _oRouteID RouteID AUTO
    JOIN_MODE = Inner
    JOINED -> AttributeManager_2
AttributeManager_2
    ATTR_TABLE:
      RENAME_SET_VALUE _oErrCode > ERROR_ CODE
      RENAME_SET_VALUE _oErrDesc > DESCRIPTION
      RENAME_SET_VALUE _oRouteID > ROUTE_ID
      RENAME_SET_VALUE Measure > ALPHA_MEAS
      RENAME_SET_VALUE _oLength > LENGTH
      RENAME_SET_VALUE _oMeasure1 > MEASURE_1
      RENAME_SET_VALUE _oMeasure2 > MEASURE_2
      RENAME_SET_VALUE _oNetworkID > NETWORK_ID
      REMOVE _oPartNo
      REMOVE _oBegPT
      REMOVE _oEndPT
      REMOVE _pt1x
      REMOVE _pt1y
      REMOVE _pt2x
      REMOVE _pt2y
      REMOVE RouteID
    -> VariableRetriever_5
VariableRetriever_5
    SCOPE = Global
    VALUE_ATTR = path
    VARNAME = _v_path_qc_output
    -> VariableRetriever
VariableRetriever
    SCOPE = Global
    VALUE_ATTR = suffix
    VARNAME = _v_suffix_output_report
    -> FWT-Excel_2 [Output]

FME custom transformer LRS_GetRouteMeas
Get Begin and End measures for Route Segments

Parameters:
- pNodeXY = No   # Include coordinates for end nodes?
- pPrecision = 5   # Measure Precision

Input (input)
    -> Deaggregator
Output (output)

Bookmark: Extract measures
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> NAM-PartNo
NAM-PartNo: NullAttributeMapper
    ATTRCHOICE = Selected Attributes
    ATTRLIST = _part_number
    NEW_VALUE = 0
    NULL_TREATMENT = New Value
    SOURCE_ATTR_VAL = Null Empty "Missing (Selected Attributes Only)"
    -> ME_BEGIN
ME_BEGIN: MeasureExtractor
    GEOM_TYPE = Individual Vertex by Index
    INDEX = 0
    MEASURE_ATTR = _oBegMeas
    -> ME_END
ME_END: MeasureExtractor
    GEOM_TYPE = Individual Vertex by Index
    INDEX = -1
    MEASURE_ATTR = _oEndMeas
    -> TST-NodeXY

Bookmark: Extract Coordinates
TST-NodeXY: Tester
    BOOL_OP = OR
    TEST_CLAUSE = TEST $(pNodeXY) = Yes
    TEST_MODE = TEST
    PASSED -> CE_BEGIN
    FAILED -> AttributeManager
CE_BEGIN: CoordinateExtractor
    IND = 0
    MODE = Specify Coordinate
    X_ATTR = _oBegX
    Y_ATTR = _oBegY
    Z_ATTR = _oBegZ
    -> CE_END
CE_END: CoordinateExtractor
    IND = -1
    MODE = Specify Coordinate
    X_ATTR = _oEndX
    Y_ATTR = _oEndY
    Z_ATTR = _oEndZ
    -> AttributeCreator
AttributeCreator
    ATTR_TABLE:
      SET_TO _oBegPT = @Value(_oBegX), @Value(_oBegY)
      SET_TO _oEndPT = @Value(_oEndX), @Value(_oEndY)
    -> AttributeManager
AttributeManager
    ATTR_TABLE:
      RENAME_SET_VALUE _part_number > _oPartNo
      SET_TO _oBegMeas = @round(@Value(_oBegMeas),$(pPrecision))
      SET_TO _oEndMeas = @round(@Value(_oEndMeas),$(pPrecision))
      REMOVE _oBegX
      REMOVE _oBegY
      REMOVE _oBegZ
      REMOVE _oEndX
      REMOVE _oEndY
      REMOVE _oEndZ
      REMOVE _geometry_name
    -> Output (output)

FME custom transformer LRS_MeasureChecker
This transformer checks whether the input features have any measures. Features output from the "True" port have measures
 while features output from the "False" port do not.

Input (input)
    -> PythonCaller
PythonCaller
    NEW_ATTRIBUTES = hasMeasures
    PYTHONSOURCE:
      import fme
      import fmeobjects
      # Template Function interface:
      # When using this function, make sure its name is set as the value of
      # the 'Class or Function to Process Features' transformer parameter
      def processFeature(feature):
          geom = feature.getGeometry()
          meas = geom.hasMeasures()
          if meas:
              feature.setAttribute("hasMeasures", "true")
          else:
              feature.setAttribute("hasMeasures", "false")
    PYTHONSYMBOL = processFeature
    -> Tester
Tester
    BOOL_OP = OR
    TEST_CLAUSE = TEST @Value(hasMeasures) = true
    TEST_MODE = TEST
    PASSED -> True (output)
    FAILED -> False (output)
True (output)
False (output)

FME custom transformer LRS_RouteQCer_edit
Comprehensive LRS Route QC

Parameters:
- pQCRules = MON SGS SPK USH
- pLRS_Route_ID = NLF_ID   # "" Route ID column
- pNumNetworks = 1   # Number of Networks Allowed *
- pMinSegLength = 2   # Min. allowable segment/gap size **
- pPrecisionCS = 6   # Coordinate System Precision
- pPrecisionMeas = 5   # Measure Precision
- pSpikeAngle = 25   # Maximum Spike Angle
- pMsg =

LRS_Route_System (input)
    -> AC_ROUTE_ID
AttributeRenamer_2
    ATTR_TABLE = RENAME_SET_DEFAULT _pLRS_Route_ID > _oRouteID
    MISSING_INPUT_ATTRS = REMOVE
    -> AVM-Err-Code
AttributeRenamer
    ATTR_TABLE = RENAME_SET_DEFAULT _oMeasure > _measure1
    MISSING_INPUT_ATTRS = REMOVE
    -> AttributeManager_3
AttributeManager_3
    ATTR_TABLE:
      RENAME_SET_VALUE _pLRS_Route_ID > _oRouteID
      RENAME_SET_VALUE _measure1 > _oMeasure1
      RENAME_SET_VALUE _length > _oLength
      RENAME_SET_VALUE _pt1x > _oPt1x
      RENAME_SET_VALUE _pt1y > _oPt1y
      RENAME_SET_VALUE _network_id > _oNetworkID
      RENAME_SET_VALUE _pt2x > _oPt2x
      RENAME_SET_VALUE _pt2y > _oPt2y
      RENAME_SET_VALUE _measure2 > _oMeasure2
    -> Junction
AttributeManager
    ATTR_TABLE:
      RENAME_SET_VALUE _length > _oLength
      RENAME_SET_VALUE _pt1x > _oPt1x
      RENAME_SET_VALUE _pt1y > _oPt1y
      RENAME_SET_VALUE _pt2x > _oPt2x
      RENAME_SET_VALUE _pt2y > _oPt2y
      RENAME_SET_VALUE _network_id > _oNetworkID
      RENAME_SET_VALUE _pLRS_Route_ID > _oRouteID
      RENAME_SET_VALUE _oTMeas > _oMeasure2
      RENAME_SET_VALUE _oFMeas > _oMeasure1
    -> AVM-Err-Code
AVM-Err-Code: AttributeValueMapper
    DEFAULT_VALUE = @Value(_oErrCode)
    DIRECTION = Forward (Source To Destination)
    LUT = SSG,Short Segment / Overshoots,SGP,Short Gaps,NWK,Network,PSN,Psuedonodes,USH,Undershoots,SPK,Spike,GSI,Grade Seperation,DIR,Measure Direction,MOC,Monotonicity - Contiguous,MOB,Monotonocity - Broken,GEO,Invalid Geometry,NUL,Null value in NonNull Field,UNQ,Duplicate ID Field,MEA,Missing Measures,LPP,Lollipop Route,NLN,Not a line geometry
    SRC = _oErrCode
    VAL_ATTR = _oErrDesc
    -> Junction
Junction
    -> AttributeRounder
Note: set output measure precision
AttributeRounder
    PLACES = $(pPrecisionMeas)
    ROUND_TYPE = Nearest
    SRC_ATTRS = _oMeasure1 _oMeasure2
    -> AttributeRounder_2
Note: set output length precision
AttributeRounder_2
    PLACES = $(pPrecisionCS)
    ROUND_TYPE = Nearest
    SRC_ATTRS = _oLength
    -> AttributeManager_4
Note: sequence the output
AttributeManager_4
    ATTR_TABLE:
      REMOVE _oPt1x
      REMOVE _oPt1y
      REMOVE _oPt2x
      REMOVE _oPt2y
    -> QC_Report (output)
    -> QC_Summarizer_2 [QC_Output]
QC_Report (output)
StatisticsCalculator_2
    CALCULATION_MODE = NUMERIC
    FEAT_STATS = _pLRS_Route_ID,NUMERIC_MODE,,,COUNT,,,,,,,,,,
    SUMMARY -> QC_Summarizer_2 [QC_Input]
Note: This needs to be linked. Check the version used in the V4 of this transformer
QC_Summarizer_2
    _pErrCode = @Value(_oErrCode)
    pInputCol = _oRouteID
    pRouteCount = @Value(_pLRS_Route_ID.total_count)
    Summary_output -> Summary (output)
Summary (output)

Bookmark: Attribute & Geometry QC
AC_ROUTE_ID: AttributeCreator
    ATTR_TABLE = SET_TO _pLRS_Route_ID = @Value($(pLRS_Route_ID))
    -> AttributeKeeper
AttributeKeeper
    CREATE_BULK_MODE_FEATURES = NO
    KEEP_ATTRS = _pLRS_Route_ID
    -> ATV-Unique
    -> StatisticsCalculator_2
ATV-Unique: AttributeValidator
    TABLE = _pLRS_Route_ID;ATTRIBUTE_UNIQUE;<Unused>
    PASSED -> GeometryFilter
    FAILED -> AttributeKeeper_2
AttributeKeeper_2
    CREATE_BULK_MODE_FEATURES = NO
    KEEP_ATTRS = _pLRS_Route_ID
    -> ACR-Error_3
ACR-Error_3: AttributeCreator
    ATTR_TABLE:
      SET_TO _oErrCode = UNQ
      SET_TO _oErrDesc = Duplicate Route ID
    -> Junction_2
GeometryFilter
    BREAK_AGG = No
    GEOM_PORT_NAMES = Line
    LINE -> GeometryValidator
    <UNFILTERED> -> ACR-Error_4
ACR-Error_4: AttributeCreator
    ATTR_TABLE:
      SET_TO _oErrCode = NLN
      SET_TO _oErrDesc = Not a line geometry
    -> Junction_2
GeometryValidator
    ISSUE_ATTR_NAME = _issues
    PRESETS = Custom
    REPAIR = No
    RULES = NAN_REMOVAL PROCESS_MEASURE]NO]FME_CONTROLLER_QUERY_FILE]transformers\dependencies\geometryvalidator\NAN_REMOVAL.fme NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers\dependencies\geometryvalidator\TYPE_REPAIR.fme NULL_REMOVAL FME_CONTROLLER_QUERY_FILE]transformers/dependencies/geometryvalidator8/NULL_REMOVAL.fme]FME_CONTROLLER_CHOICE]NULL_REMOVAL OGC_SIMPLE_CHECK FME_CONTROLLER_QUERY_FILE]transformers/dependencies/geometryvalidator8/OGC_SIMPLE_CHECK.fme]FME_CONTROLLER_CHOICE]OGC_SIMPLE_CHECK]LEGACY_OGC]No MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator/MISSING_MEASURES_AND_ELEVATIONS.fme
    SUMMARY = Detailed
    PASSED -> LRS_MeasureChecker
    FAILED -> GeometryRemover
    FAILED -> LollipopIdentifier
LollipopIdentifier
    _PLRS_ROUTE_ID = @Value(_pLRS_Route_ID)
    Lollipops -> ACR-Error_5
    Other -> FeatureJoiner [LEFT]
ACR-Error_5: AttributeCreator
    ATTR_TABLE:
      SET_TO _oErrCode = LPP
      SET_TO _oErrDesc = Lollipop Route
    -> Junction_2
Junction_2
    -> AttributeRenamer_2
GeometryRemover
    -> FeatureJoiner [RIGHT]
FeatureJoiner
    ATTR_CONFLICT_RES = Use Left
    GEOMETRY_HANDLING = Use Right
    JOIN_KEYS = _pLRS_Route_ID _pLRS_Route_ID AUTO
    JOIN_MODE = Inner
    JOINED -> ACR-Error_2
ACR-Error_2: AttributeCreator
    ATTR_TABLE:
      SET_TO _oErrCode = GEO
      SET_TO _oErrDesc = @Value(_issues{0}.issue_found)
    -> AK
LRS_MeasureChecker
    True -> AK_2
    False -> ACR-Error
ACR-Error: AttributeCreator
    ATTR_TABLE = SET_TO _oErrCode = NME
    -> AK
AK_2: AttributeKeeper
    CREATE_BULK_MODE_FEATURES = NO
    KEEP_ATTRS = _pLRS_Route_ID
    -> TST-OTHER
    -> TST-MON
    -> TST-DIR
    -> TST-GSI
    -> TST-SPK
    -> LRS_RevGeoCoder_3 [LRS_Route_Feature]

Bookmark: Geometry/Topo QC
AK: AttributeKeeper
    CREATE_BULK_MODE_FEATURES = NO
    KEEP_ATTRS = _pLRS_Route_ID,_oErrCode,_oErrDesc
    -> AttributeManager_3
TST-MON: Tester
    BOOL_OP = OR
    TEST_CLAUSE = TEST $(pQCRules) CONTAINS MON
    TEST_MODE = TEST
    PASSED -> LRS_RouteMonoHandler [Route]
LRS_RouteMonoHandler
    p_FixMeasure = No
    p_Route_ID = _pLRS_Route_ID
    MOX_Report -> AttributeManager_3
    MOD_Report -> AttributeRenamer
TST-DIR: Tester
    BOOL_OP = OR
    TEST_CLAUSE = TEST $(pQCRules) CONTAINS DIR
    TEST_MODE = TEST
    PASSED -> LRS_RouteQCer_DIR [Route_System]
LRS_RouteQCer_DIR
    _PLRS_ROUTE_ID = @Value(_pLRS_Route_ID)
    -> AttributeManager_3
TST-OTHER: Tester
    BOOL_OP = OR
    TEST_CLAUSE:
      TEST $(pQCRules) CONTAINS SGS
      TEST $(pQCRules) CONTAINS USH
      TEST $(pQCRules) CONTAINS NWK
      TEST $(pQCRules) CONTAINS PSN
    TEST_MODE = TEST
    PASSED -> LRS_RouteQCer_OTH [Route_System]
LRS_RouteQCer_OTH
    PNUMNETWORKS = $(pNumNetworks)
    PQCRULES = $(pQCRules)
    _PLRS_ROUTE_ID = @Value(_pLRS_Route_ID)
    pMinSegLength = $(pMinSegLength)
    -> TestFilter
TST-GSI: Tester
    BOOL_OP = OR
    TEST_CLAUSE = TEST $(pQCRules) CONTAINS GSI
    TEST_MODE = TEST
    PASSED -> LRS_RouteQcer_GSI [Route_System]
LRS_RouteQcer_GSI
    pLRS_Route_ID = _pLRS_Route_ID
    -> AttributeCreator_2
TST-SPK: Tester
    BOOL_OP = OR
    TEST_CLAUSE = TEST $(pQCRules) CONTAINS SPK
    TEST_MODE = TEST
    PASSED -> LRS_RouteQCer_SPK [Route_System]
LRS_RouteQCer_SPK
    _PLRS_ROUTE_ID = @Value(_pLRS_Route_ID)
    pSpikeAngle = $(pSpikeAngle)
    -> AttributeCreator_2

Bookmark: Get measures
TestFilter
    DEFAULT_VALUE = NoPoint
    PASSED_TEST_GROUP_OUTPUT = FIRST
    TEST_LIST = "BOOL_OP,OR,COMPOSITE_TEST,""""""1"""""",TEST_CLAUSE,TEST @Value(_oErrCode) IN PSN,SPK",SinglePoint,"BOOL_OP,OR,COMPOSITE_TEST,""""""1"""""",TEST_CLAUSE,TEST @Value(_oErrCode) IN SSG,SGP",DualPoint
    SinglePoint -> AttributeCreator_2
    DualPoint -> LRS_RevGeoCoder_3 [Event_XY]
    NoPoint -> AttributeManager_3
Note: Make as a point event
AttributeCreator_2
    ATTR_TABLE:
      SET_TO _pt2x = @Value(_pt1x)
      SET_TO _pt2y = @Value(_pt1y)
    -> LRS_RevGeoCoder_3 [Event_XY]
Note: embedded v 2.
Note: Ignor revgeocode errors
LRS_RevGeoCoder_3
    pLRS_Route_ID = _pLRS_Route_ID
    pRoute_ID = _pLRS_Route_ID
    pTolerance = 0
    pX_From = _pt1x
    pX_To = _pt2x
    pY_From = _pt1y
    pY_To = _pt2y
    -> AttributeManager

FME custom transformer TabularSummary
Expand the summary QC in json to tabular form

Parameters:
- _ERROR_COUNT = @Value(_error_count)   # Error Count
- _INPUT_COUNT = @Value(_Input_count)   # Input Count
- _RESULT = @Value(_result)   # Result

Input (input)
    -> JSONFragmenter
JSONFragmenter
    EXPLODE_FORMAT = JSON
    EXTRACT_ATTR = No
    JSON_ATTR = _result
    JSON_QUERY = json["result"]
    READ_FROM_FILE = NO
    REJECT_EMPTY_LISTS = YES
    FRAGMENTS -> TST-ERR
TST-ERR: Tester
    BOOL_OP = OR
    TEST_CLAUSE = TEST @Value(_error_count) > 0
    TEST_MODE = TEST
    PASSED -> JSONFragmenter_2
    FAILED -> AttributeManager_2
JSONFragmenter_2
    EXPLODE_FORMAT = JSON
    EXTRACT_ATTR = No
    JSON_ATTR = _result
    JSON_QUERY = json[*]
    READ_FROM_FILE = NO
    REJECT_EMPTY_LISTS = YES
    FRAGMENTS -> JSONFlattener
JSONFlattener
    ERROR_LIST_ATTR = _json_error
    JSON_DOCUMENT = @Value(_result)
    READ_FROM_FILE = NO
    RECURSIVE = Yes
    -> AttributeExposer
AttributeExposer
    ATTR_LIST = _oErrCode,_oErrCode.total_count
    -> AttributeManager_3
AttributeManager_3
    ATTR_TABLE:
      REMOVE _result
      RENAME_SET_VALUE _error_count > Total Error Count
      RENAME_SET_VALUE _Input_count > Input Count
      REMOVE json_type
      REMOVE json_index
      RENAME_SET_VALUE _oErrCode > Error Code
      RENAME_SET_VALUE _oErrCode.total_count > Count
    -> Output (output)
AttributeManager_2
    ATTR_TABLE:
      REMOVE _result
      RENAME_SET_VALUE _error_count > Total Error Count
      RENAME_SET_VALUE _Input_count > Input Count
      REMOVE json_type
      REMOVE json_index
    -> Output (output)
Output (output)

FME custom transformer LRS_RouteQCer_OTH
Most common topological Error checking

Parameters:
- PNUMNETWORKS = @Value(_pNumNetworks)   # Num of Networks allowed
- PQCRULES = @Value(_pQCRules)   # QC Rules
- _PLRS_ROUTE_ID = @Value(_pLRS_Route_ID)   # Plrs Route Id
- pMinSegLength = 10   # Min. allowable segment/gap size (CS UOM)

AC_ROUTES: AttributeCreator [off]
    ATTR_TABLE:
      SET_TO _ROUTE_0 = _node_angle{0}._pLRS_Route_ID
      SET_TO _ROUTE_1 = _node_angle{1}._pLRS_Route_ID
    -> ILQ_PSEUDO [TOPO_NODES] [off]
ILQ_PSEUDO: InlineQuerier [off]
    QUERY_DEF:
      PSEUDO_NODES,select "_ROUTE_0" _pLRS_Route_ID
      ,"fme_feature_content"
      from "TOPO_NODES"
      WHERE "_element_count" = 2 and "_ROUTE_0" = "_ROUTE_1"




      ,FIRST
    QUERY_SCHEMA = PSEUDO_NODES,_pLRS_Route_ID,varchar(20),TOPO_NODES.fme_feature_content,fme_feature_content
    TABLE_DEF = TOPO_NODES,_ROUTE_0,varchar(20),_ROUTE_1,varchar(20),_node_angle{}._pLRS_Route_ID,varchar(20),_node_angle{}.fme_direction,integer,_element_count,integer
Route_System (input)
    -> TPB_UNCLEAN
TPB_UNCLEAN: TopologyBuilder
    ALLOW_CYCLES = No
    BOUNDING_EDGES = All
    CLEANING_TOLERANCE = None
    DEAGGREGATE_INPUT = Yes
    GENERATION_MODE = INTERSECT
    LIST_NAME_EDGES = _node_angle
    MAX = 0
    OVERLAPPING_MODE = No
    NODE -> Tester
    NODE -> TST-USH
    NODE -> TST-PSN
    LINE -> Tester_4
    LINE -> NF_NODE_EDGE [BASE]
    LINE -> AttributeKeeper_2
AC_PSN: AttributeCreator
    ATTR_TABLE = SET_TO _oErrCode = PSN
    -> AC_PSN_OUTPUT_-__NF_SMALL_GAPS_Matched
AC_PSN_OUTPUT_-__NF_SMALL_GAPS_Matched: Junction
    -> ARN
ARN: AttributeRenamer
    ATTR_TABLE = RENAME_SET_DEFAULT _distance > _length
    -> Output (output)
Output (output)

Bookmark: Small Route Gaps or Segments
Tester
    BOOL_OP = OR
    TEST_CLAUSE = TEST $(PQCRULES) CONTAINS SGS
    TEST_MODE = TEST
    PASSED -> AK_2
AK_2: AttributeKeeper
    CREATE_BULK_MODE_FEATURES = No
    KEEP_ATTRS = _pLRS_Route_ID,_node_number
    -> NF_SMALL_GAPS [CANDIDATE]
NF_SMALL_GAPS: NeighborFinder
    ATTR_ACCUM_MODE = Prefix Candidate
    INCOMING_PREFIX = _fme
    INSERT_VERTEX = No
    K = 1
    MAX = $(pMinSegLength)
    MEASURES_FROM_CANDIDATE = No
    MEASURE_TYPE = Continuous
    MODE = Candidates Only
    TREAT_POLYGON_AS = Lines
    MATCHED -> ILQ_SHORT [Close_Points]
AttributeKeeper_2
    CREATE_BULK_MODE_FEATURES = NO
    KEEP_ATTRS = _edge_id,_from_node,_pLRS_Route_ID,_to_node
    -> ILQ_SHORT [Edges]
ILQ_SHORT: InlineQuerier
    QUERY_DEF:
      Short_Seg,SELECT B."_pLRS_Route_ID"
      , A."_closest_base_x" _pt1x
      , A."_closest_base_y" _pt1y
      , A."_closest_candidate_x" _pt2x
      , A."_closest_candidate_y" _pt2y
      , A."_distance"
      , B."fme_feature_content"
      FROM "Close_Points" A
      , "Edges" B
      WHERE (B."_from_node" = A."_fme_node_number" AND B."_to_node" = A."_node_number")
       OR (B."_from_node" = A."_node_number" AND B."_to_node" = A."_fme_node_number")





      ,FIRST,Short_gap,SELECT B."_pLRS_Route_ID"
      , A."_closest_base_x" _pt1x
      , A."_closest_base_y" _pt1y
      , A."_closest_candidate_x" _pt2x
      , A."_closest_candidate_y" _pt2y
      , A."_distance"
      , A."fme_feature_content"
      FROM "Close_Points" A
      , "Edges" B
      , "Edges" C
      WHERE NOT EXISTS ( SELECT 1
                        FROM "Edges" D
                        WHERE (D."_from_node" = A."_fme_node_number" AND D."_to_node" = A."_node_number")
                               OR (D."_from_node" = A."_node_number" AND D."_to_node" = A."_fme_node_number")
      )  -- remove short segment form consideration
      AND C."_pLRS_Route_ID" = B."_pLRS_Route_ID"  -- limit to nodes on common route
      AND B."_edge_id" < C."_edge_id"  -- only join once
      AND (B."_from_node" = A."_fme_node_number" AND C."_from_node" = A."_node_number"
           OR B."_from_node" = A."_node_number" AND C."_from_node" = A."_fme_node_number"
           OR B."_from_node" = A."_fme_node_number" AND C."_to_node" = A."_node_number"
           OR B."_from_node" = A."_node_number" AND C."_to_node" = A."_fme_node_number"
            OR B."_to_node" = A."_fme_node_number" AND C."_from_node" = A."_node_number"
           OR B."_to_node" = A."_node_number" AND C."_from_node" = A."_fme_node_number"
          OR B."_to_node" = A."_fme_node_number" AND C."_to_node" = A."_node_number"
           OR B."_to_node" = A."_node_number" AND C."_to_node" = A."_fme_node_number"
      )     -- two segments each takes one of the node pair.
      ,FIRST
    QUERY_SCHEMA = Short_Seg,_pLRS_Route_ID,varchar(20),_pt1x,float,_pt1y,float,_pt2x,float,_pt2y,float,_distance,float,Edges.fme_feature_content,fme_feature_content,Short_gap,_pLRS_Route_ID,varchar(20),_pt1x,float,_pt1y,float,_pt2x,float,_pt2y,float,_distance,float,Close_Points.fme_feature_content,fme_feature_content
    TABLE_DEF = Edges,_pLRS_Route_ID,varchar(20),_edge_id,integer,_from_node,integer,_to_node,integer,Close_Points,_fme_node_number,integer,_node_number,integer,_closest_candidate_x,float,_closest_candidate_y,float,_closest_base_x,float,_closest_base_y,float,_distance,float
    Short_Seg -> ARM_2
    Short_gap -> ARM
ARM_2: AttributeRemover
    REMOVE_ATTRS = _to_node,_edge_id,_from_node
    -> AC_SSG
AC_SSG: AttributeCreator
    ATTR_TABLE = SET_TO _oErrCode = SSG
    -> GP_MULTI_POINTS
ARM: AttributeRemover
    REMOVE_ATTRS = _fme_pLRS_Route_ID,_closest_candidate_x,_candidate_angle,_candidate_label_angle,_closest_candidate_y,_closest_base_x,_closest_base_y,_node_number,_angle,_fme_node_number
    -> AC_SGP
AC_SGP: AttributeCreator
    ATTR_TABLE = SET_TO _oErrCode = SGP
    -> GP_MULTI_POINTS
GP_MULTI_POINTS: GeometryReplacer
    KIND_LONG = OGC Well Known Text
    OGC_WKT_PRECISION_DISPLAY = 64-bit
    REMOVE_ATTRIBUTE = Yes
    SOURCE = MULTIPOINT (@Value(_pt1x) @Value(_pt1y), @Value(_pt2x) @Value(_pt2y))
    -> AC_PSN_OUTPUT_-__NF_SMALL_GAPS_Matched

Bookmark: Psuedo Nodes
TST-PSN: Tester
    BOOL_OP = OR
    TEST_CLAUSE = TEST $(PQCRULES) CONTAINS PSN
    TEST_MODE = TEST
    PASSED -> ACR-RouteID
Note: Get the first route id
ACR-RouteID: AttributeCreator
    ATTR_TABLE = SET_TO _pLRS_Route_ID = @Value(_node_angle{0}._pLRS_Route_ID)
    -> AK
AK: AttributeKeeper
    CREATE_BULK_MODE_FEATURES = NO
    KEEP_ATTRS = _pLRS_Route_ID
    KEEP_LIST = _node_angle{}._pLRS_Route_ID
    -> LEC
LEC: ListElementCounter
    CNT_ATTR = _element_count
    LIST_NAME = _node_angle{}
    -> TST-2Links
TST-2Links: Tester
    BOOL_OP = COMPOSITE
    COMPOSITE_TEST = 1 AND 2
    TEST_CLAUSE:
      TEST @Value(_element_count) = 2
      TEST @Value(_node_angle{0}._pLRS_Route_ID) = @Value(_node_angle{1}._pLRS_Route_ID)
    TEST_MODE = TEST
    PASSED -> AK_3
AK_3: AttributeKeeper
    CREATE_BULK_MODE_FEATURES = No
    KEEP_ATTRS = _pLRS_Route_ID
    -> CE_NODE
CE_NODE: CoordinateExtractor
    IND = 0
    MODE = Specify Coordinate
    X_ATTR = _pt1x
    Y_ATTR = _pt1y
    -> AC_PSN

Bookmark: Undershoots and Overshoots
Note: Make this for Undershoots only. Overshoots are short route segments
TST-USH: Tester
    BOOL_OP = OR
    TEST_CLAUSE = TEST $(PQCRULES) CONTAINS USH
    TEST_MODE = TEST
    PASSED -> NF_NODE_EDGE [CANDIDATE]
Note: Make list of candidates
NF_NODE_EDGE: NeighborFinder
    ATTR_ACCUM_MODE = Merge Candidate
    ATTR_CONFLICT_RES = Use Base
    CANDIDATES_FIRST = No
    CLOSE_LIST_ATTRS_TO_INCLUDE_MODE = All Attributes
    CLOSE_LIST_NAME = _candidates
    INSERT_VERTEX = No
    K = 5
    MAX = 100
    MEASURES_FROM_CANDIDATE = No
    MEASURE_TYPE = Continuous
    MODE = Bases and Candidates
    TREAT_POLYGON_AS = Lines
    MATCHED -> LEC_EDGES
Note: Count number of elements in list
LEC_EDGES: ListElementCounter
    CNT_ATTR = _element_count
    LIST_NAME = _candidates{}
    -> TSF
Note: Test for more than one element in list
TSF: TestFilter
    DEFAULT_VALUE = <UNFILTERED>
    PASSED_TEST_GROUP_OUTPUT = FIRST
    TEST_LIST:
      BOOL_OP,AND,COMPOSITE_TEST,<Unused>,TEST_CLAUSE,"TEST @Value(_element_count) NOT_> 1
      TEST @Value(_distance) NOT_= 0",Under_Overs
    Under_Overs -> AK_4
AK_4: AttributeKeeper
    CREATE_BULK_MODE_FEATURES = No
    KEEP_ATTRS = _distance,_pLRS_Route_ID
    -> CE_PT
CE_PT: CoordinateExtractor
    IND = 0
    MODE = Specify Coordinate
    X_ATTR = _pt1x
    Y_ATTR = _pt1y
    -> VertexCreator
Note: replace geom with this point!
VertexCreator
    IGNORE_DUPLICATES = No
    MEASURE_TYPE = Continuous
    MISSING_VAL_MODE = Compute
    MODE_NAME = Add Point
    XVAL = @Value(_pt1x)
    YVAL = @Value(_pt1y)
    -> AC_USH
AC_USH: AttributeCreator
    ATTR_TABLE = SET_TO _oErrCode = USH
    -> AC_PSN_OUTPUT_-__NF_SMALL_GAPS_Matched

Bookmark: Connectivity Check
Tester_4
    BOOL_OP = OR
    TEST_CLAUSE = TEST $(PQCRULES) CONTAINS NWK
    TEST_MODE = TEST
    PASSED -> AttributeKeeper
AttributeKeeper
    CREATE_BULK_MODE_FEATURES = No
    KEEP_ATTRS = _edge_id,_pLRS_Route_ID
    -> NTC [LINE]
NTC: NetworkTopologyCalculator
    NETWORK_ID_ATTR = _network_id
    NETWORK -> DuplicateFilter_2
DuplicateFilter_2
    INPUT_ORDERED_CHOICE = No
    KEYATTR = _network_id _pLRS_Route_ID
    UNIQUE -> SC_NETWORKS
SC_NETWORKS: StatisticsCalculator
    CALCULATION_MODE = NUMERIC
    FEAT_STATS = _network_id,NUMERIC_MODE,,MAX,,,,,,,,,,
    PREPEND_ATTR_NAME_OBS = No
    STATISTIC_SUFFIX_RENAME_MAP = MAX,_max
    COMPLETE -> TestFilter_2
TestFilter_2
    DEFAULT_VALUE = <UNFILTERED>
    PASSED_TEST_GROUP_OUTPUT = FIRST
    TEST_LIST = BOOL_OP,OR,COMPOSITE_TEST,<Unused>,TEST_CLAUSE,"TEST @Value(_network_id) > $(PNUMNETWORKS)",Unconnected
    Unconnected -> AR
AR: AttributeRemover
    REMOVE_ATTRS = _max,_edge_id
    -> AC_NWK
AC_NWK: AttributeCreator
    ATTR_TABLE = SET_TO _oErrCode = NWK
    -> AC_PSN_OUTPUT_-__NF_SMALL_GAPS_Matched

FME custom transformer LRS_RevGeoCoder
Convert point features into LRS Events
Input parameters:
    Events: Route ID, From X/Y, To X/Y
    LRS System: Route ID 
    Lateral offset tolerance in spatial reference distance UOM

Parameters:
- pLRS_Route_ID =   # " " Route ID column in LRS Route System
- pRoute_ID =   # " " Route ID column in input source
- pX_From =   # " " From point X Coord column in input source
- pY_From =   # " " From point Y Coord column in input source
- pX_To =   # " " To point X Coord column in input source
- pY_To =   # " " To point Y Coord column in input source
- pTolerance = 0   # Lateral offset tolerance

Event_XY (input)
    -> Counter
LRS_Route_Feature (input)
    -> AC_ROUTE
AttributeManager_2
    ATTR_TABLE:
      REMOVE _pX
      REMOVE _pY
      REMOVE _pRoute_ID
    -> FeatureJoiner_5 [RIGHT]

Bookmark: Event filter by route RouteID
Note: Internal id for linking back the geometry
Counter
    CNT_ATTR = _count
    DOMAIN = counter
    SCOPE = Global
    START = 0
    -> GeometryRemover
    -> FeatureJoiner_4 [LEFT]
    -> FeatureJoiner_5 [LEFT]
GeometryRemover
    -> AC_SOURCE_3
AC_SOURCE_3: AttributeCreator
    ATTR_TABLE = SET_TO _pRoute_ID = @Value($(pRoute_ID))
    -> AttributeKeeper_2
    -> FeatureJoiner_2 [LEFT]
FeatureJoiner_2
    ATTR_CONFLICT_RES = Use Left
    GEOMETRY_HANDLING = Use Left
    JOIN_KEYS = _pRoute_ID _pRoute_ID AUTO
    JOIN_MODE = Inner
    JOINED -> AC_SOURCE_2
    JOINED -> TF_POINT_LINE
    UNJOINED_LEFT -> GRM_3

Bookmark: route filter by event RouteID
AttributeKeeper_2
    CREATE_BULK_MODE_FEATURES = NO
    KEEP_ATTRS = _pRoute_ID
    -> DuplicateFilter
DuplicateFilter
    INPUT_ORDERED_CHOICE = No
    KEYATTR = _pRoute_ID
    UNIQUE -> FeatureJoiner [LEFT]
AC_ROUTE: AttributeCreator
    ATTR_TABLE = SET_TO _pRoute_ID = @Value($(pLRS_Route_ID))
    -> FeatureJoiner [RIGHT]
FeatureJoiner
    ATTR_CONFLICT_RES = Use Right
    GEOMETRY_HANDLING = Use Right
    JOIN_KEYS = _pRoute_ID _pRoute_ID AUTO
    JOIN_MODE = Inner
    JOINED -> Deaggregator
    JOINED -> FeatureJoiner_2 [RIGHT]

Bookmark: Prepare Events and routes
Note: from node
AC_SOURCE_2: AttributeCreator
    ATTR_TABLE:
      SET_TO _pX = @Value($(pX_From))
      SET_TO _pY = @Value($(pY_From))
      SET_TO _oTopo = 0
    -> VC_FROM
TF_POINT_LINE: TestFilter
    DEFAULT_VALUE = LINE
    PASSED_TEST_GROUP_OUTPUT = FIRST
    TEST_LIST:
      BOOL_OP,AND,COMPOSITE_TEST,<Unused>,TEST_CLAUSE,"TEST @Value($(pX_From)) = @Value($(pX_To))
      TEST @Value($(pY_From)) = @Value($(pY_To))",POINT
    LINE -> AC_SOURCE
Note: to node
AC_SOURCE: AttributeCreator
    ATTR_TABLE:
      SET_TO _pX = @Value($(pX_To))
      SET_TO _pY = @Value($(pY_To))
      SET_TO _oTopo = 1
    -> VC_FROM
VC_FROM: VertexCreator
    IGNORE_DUPLICATES = No
    MEASURE_TYPE = Continuous
    MISSING_VAL_MODE = None (Drop Values)
    MODE_NAME = Add Point
    XVAL = @Value(_pX)
    YVAL = @Value(_pY)
    -> POLO_2 [POINT]
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeKeeper_4
AttributeKeeper_4
    CREATE_BULK_MODE_FEATURES = NO
    KEEP_ATTRS = _part_number,_pRoute_ID
    -> MeasureExtractor
MeasureExtractor
    GEOM_TYPE = Whole Line
    MEASURE_LIST = _measures
    -> MeasureSetter
Note: Naming measure allows the point on line overlayer to store multiple measures and retrieve the appripriate measure from the correct route
MeasureSetter
    GEOM_TYPE = Whole Line
    MEASURE_LIST = _measures{}
    MEASURE_NAME = @Value(_pRoute_ID)
    -> AttributeRemover_3
AttributeRemover_3
    LIST_ATTRS = _measures{}
    -> GeometryFilter
GeometryFilter
    BREAK_AGG = No
    GEOM_PORT_NAMES = Line
    LINE -> POLO_2 [LINE]
    <UNFILTERED> -> AttributeManager

Bookmark: Error Handling
GRM_3: GeometryRemover
    -> AC_ERROR
AC_ERROR: AttributeCreator
    ATTR_TABLE:
      SET_TO _oErrCode = EXT
      SET_TO _oErrDesc = Route referenced by source does not exist
    -> AttributeManager_3
GRM_5: GeometryRemover
    -> AC_ERROR_2
AC_ERROR_2: AttributeCreator
    ATTR_TABLE:
      SET_TO _oErrDesc = FME_CONDITIONAL:DEFAULT_VALUE'To Point Beyond Tolerance'BOOL_OP;OR;COMPOSITE_TEST;<Unused>;TEST @Value(_oTopo) = 0'From Point Beyond Tolerance'FME_NUM_CONDITIONS2___
      SET_TO _oErrCode = TOL
    -> AttributeManager_3
AttributeManager_3
    ATTR_TABLE:
      REMOVE _pRoute_ID
      REMOVE _pX
      REMOVE _pY
      REMOVE _oTopo
      REMOVE _part_number
      REMOVE _rteList{}._pRoute_ID
      REMOVE _overlaps
    -> FeatureJoiner_4 [RIGHT]
AttributeManager
    ATTR_TABLE:
      SET_TO _oErrCode = GEO
      SET_TO _oErrDesc = Part @Value(_part_number) of @Value(_pRoute_ID) is not a line segment
      REMOVE _pRoute_ID
      REMOVE _part_number
    -> FeatureJoiner_4 [RIGHT]

Bookmark: Spatial relate and dispatching
POLO_2: PointOnLineOverlayer
    ATTR_ACCUM_MODE = Merge Incoming
    ATTR_CONFLICT_RES = Use Original
    DEAGGREGATE_INPUT = Yes
    LIST_ATTRS_TO_INCLUDE = _pRoute_ID
    LIST_NAME = _rteList
    MEASURE_TYPE = Continuous
    MERGE_MEASURES = Yes
    OV_ATTR = _overlaps
    TOLERANCE = $(pTolerance)
    POINT -> AttributeRemover_2
AttributeRemover_2
    -> TST_Tolerance
ARM: AttributeRemover
    REMOVE_ATTRS = _part_number,_overlaps,_element_index,rte_list_pRoute_ID
    -> ME_FMEAS
ME_FMEAS: MeasureExtractor
    GEOM_TYPE = Individual Vertex by Index
    INDEX = 0
    MEASURE_ATTR = _oFMeas
    MEASURE_NAME = @Value(_pRoute_ID)
    -> TF_POINT_LINE_2
TF_POINT_LINE_2: TestFilter
    DEFAULT_VALUE = LINE
    PASSED_TEST_GROUP_OUTPUT = FIRST
    TEST_LIST:
      BOOL_OP,AND,COMPOSITE_TEST,<Unused>,TEST_CLAUSE,"TEST @Value($(pX_From)) = @Value($(pX_To))
      TEST @Value($(pY_From)) = @Value($(pY_To))",POINT
    POINT -> GRM_4
    LINE -> ME_TMEAS

Bookmark: Intersection Event Handling
Note: 0 Overlaps = Beyond tolerance & will not contain list attribute
TST_Tolerance: Tester
    BOOL_OP = OR
    TEST_CLAUSE = TEST @Value(_overlaps) > 0
    TEST_MODE = TEST
    PASSED -> ListExploder
    FAILED -> GRM_5
Note: Deaggregate list features
ListExploder
    ATTR_ACCUM_MODE = Prefix List Attributes
    INCOMING_PREFIX = rte_list
    INDEX_ATTR = _element_index
    LIST_ATTR = _rteList{}
    ELEMENTS -> TST-SameRoute
Note: Process only list features where eventRouteId = LRSRouteID
TST-SameRoute: Tester
    BOOL_OP = OR
    TEST_CLAUSE = TEST @Value(rte_list_pRoute_ID) = @Value(_pRoute_ID)
    TEST_MODE = TEST
    PASSED -> ARM

Bookmark: Process Point Events
GRM_4: GeometryRemover
    -> AC_TMEAS
AC_TMEAS: AttributeCreator
    ATTR_TABLE = SET_TO _oTMeas = @Value(_oFMeas)
    -> ARM_4
ARM_4: AttributeRemover
    REMOVE_ATTRS = _oTopo
    -> AttributeManager_2

Bookmark: Process Linear Events
ME_TMEAS: MeasureExtractor
    GEOM_TYPE = Individual Vertex by Index
    INDEX = -1
    MEASURE_ATTR = _oTMeas
    MEASURE_NAME = @Value(_pRoute_ID)
    -> GRM_2
GRM_2: GeometryRemover
    -> TF_TOPO
TF_TOPO: TestFilter
    DEFAULT_VALUE = ToNodes
    PASSED_TEST_GROUP_OUTPUT = FIRST
    TEST_LIST = BOOL_OP,OR,COMPOSITE_TEST,<Unused>,TEST_CLAUSE,"TEST @Value(_oTopo) = 0",FromNodes
    FromNodes -> ARM_3
    ToNodes -> ARM_2
ARM_3: AttributeRemover
    REMOVE_ATTRS = _oTopo,_oTMeas
    -> FeatureJoiner_3 [LEFT]
ARM_2: AttributeRemover
    REMOVE_ATTRS = _oTopo,_oFMeas
    -> FeatureJoiner_3 [RIGHT]
FeatureJoiner_3
    ATTR_CONFLICT_RES = Use Left
    GEOMETRY_HANDLING = Use Left
    JOIN_KEYS = _count _count AUTO
    JOIN_MODE = Inner
    JOINED -> TST-Measures

Bookmark: re-arrange F-T measures
TST-Measures: Tester
    BOOL_OP = OR
    TEST_CLAUSE = TEST @Value(_oFMeas) > @Value(_oTMeas)
    TEST_MODE = TEST
    PASSED -> ARN-FMeasure
    FAILED -> AttributeManager_2
ARN-FMeasure: AttributeRenamer
    ATTR_TABLE = RENAME_SET_DEFAULT _oFMeas > _oTMeas1
    MISSING_INPUT_ATTRS = PRESERVE
    -> ARN-ToMeasure
ARN-ToMeasure: AttributeRenamer
    ATTR_TABLE:
      RENAME_SET_DEFAULT _oTMeas > _oFMeas
      RENAME_SET_DEFAULT _oTMeas1 > _oTMeas
    MISSING_INPUT_ATTRS = PRESERVE
    -> AttributeManager_2

Bookmark: Link Original Geometry for the pass-through pattern
FeatureJoiner_5
    ATTR_CONFLICT_RES = Use Left
    GEOMETRY_HANDLING = Use Left
    JOIN_KEYS = _count _count AUTO
    JOIN_MODE = Inner
    JOINED -> AttributeRemover
AttributeRemover
    REMOVE_ATTRS = _count
    -> Output (output)
Output (output)
FeatureJoiner_4
    ATTR_CONFLICT_RES = Use Left
    GEOMETRY_HANDLING = Use Left
    JOIN_KEYS = _count _count AUTO
    JOIN_MODE = Inner
    JOINED -> AttributeRemover_4
AttributeRemover_4
    REMOVE_ATTRS = _count
    -> Error_Log (output)
Error_Log (output)

FME custom transformer LRS_RouteQcer_GSI
Identify grade-separated intersection

Parameters:
- pLRS_Route_ID = NLF_ID   # " " Route ID column in LRS Route System

Route_System (input)
    -> AC_ROUTE_ID
AC_ROUTE_ID: AttributeCreator
    ATTR_TABLE = SET_TO _pLRS_Route_ID = @Value($(pLRS_Route_ID))
    -> TPB_CLEAN
Note: End Nodes and Collinear Segments
TPB_CLEAN: TopologyBuilder
    ALLOW_CYCLES = No
    BOUNDING_EDGES = All
    DEAGGREGATE_INPUT = Yes
    GENERATION_MODE = EXISTING
    LIST_NAME_EDGES = _node_edges
    MAX = 0
    OVERLAPPING_MODE = No
    NODE -> AC_FLAG
    LINE -> TPB_UNCLEAN
AC_FLAG: AttributeCreator
    ATTR_TABLE = SET_TO ExistingNode = 1
    -> TPB_UNCLEAN
Note: End Nodes and Intersection
TPB_UNCLEAN: TopologyBuilder
    ALLOW_CYCLES = No
    BOUNDING_EDGES = All
    CLEANING_TOLERANCE = None
    DEAGGREGATE_INPUT = Yes
    GENERATION_MODE = INTERSECT
    LIST_NAME_EDGES = _node_edges
    LIST_NAME_FACES = _faces
    LIST_NAME_NODES = _nodes
    MAX = 0
    OVERLAPPING_MODE = No
    NODE -> ListExploder
ListExploder
    ATTR_ACCUM_MODE = Merge List Attributes
    ATTR_CONFLICT_RES = Use List Attribute Values
    INDEX_ATTR = _element_index
    LIST_ATTR = _node_edges{}
    ELEMENTS -> AttributeKeeper
AttributeKeeper
    CREATE_BULK_MODE_FEATURES = NO
    KEEP_ATTRS = _node_number,_pLRS_Route_ID,ExistingNode
    -> DuplicateFilter
DuplicateFilter
    INPUT_ORDERED_CHOICE = No
    KEYATTR = _node_number _pLRS_Route_ID
    UNIQUE -> TST_NEWNODES
TST_NEWNODES: Tester
    BOOL_OP = OR
    TEST_CLAUSE = TEST @Value(ExistingNode) != 1
    TEST_MODE = TEST
    PASSED -> AK
AK: AttributeKeeper
    CREATE_BULK_MODE_FEATURES = No
    KEEP_ATTRS = _pLRS_Route_ID
    -> CE_NODES
CE_NODES: CoordinateExtractor
    IND = 0
    MODE = Specify Coordinate
    X_ATTR = _pt1x
    Y_ATTR = _pt1y
    -> AC_ERRCODE
AC_ERRCODE: AttributeCreator
    ATTR_TABLE = SET_TO _oErrCode = GSI
    -> Output (output)
Output (output)

FME custom transformer LollipopIdentifier
Identify lollipop line configurations

Parameters:
- _PLRS_ROUTE_ID = @Value(_pLRS_Route_ID)   # Plrs Route Id

Input (input)
    -> CoordinateExtractor
CoordinateExtractor
    LIST_NAME = _indices
    MODE = All Coordinates
    -> GeometryRemover
GeometryRemover
    -> AttributeRemover
AttributeRemover
    LIST_ATTRS = _issues{} _issues{}.count _issues{}.issue_found _issues{}.location_sample.x _issues{}.location_sample.y _issues{}.location_sample.z _issues{}.repair_state
    -> ListExploder
ListExploder
    ATTR_ACCUM_MODE = Merge List Attributes
    ATTR_CONFLICT_RES = Use List Attribute Values
    INDEX_ATTR = _element_index
    LIST_ATTR = _indices{}
    ELEMENTS -> StringConcatenator
StringConcatenator
    ACTION = Create New Attribute
    PARM_LINE = fme_basicstring:9%9%9:@Value(x)@Value(y)@Value(z)
    VAL_ATTR = _xyz
    -> StatisticsCalculator
StatisticsCalculator
    CALCULATION_MODE = LEXICAL
    FEAT_STATS = _element_index,LEXICAL,MIN,MAX,COUNT,<Unused>,<Unused>,,,,<Unused>,<Unused>,<Unused>,,
    GROUP_BY = _pLRS_Route_ID _xyz
    COMPLETE -> Tester
Tester
    BOOL_OP = COMPOSITE
    COMPOSITE_TEST = 1 AND ( 2 OR 3 )
    TEST_CLAUSE:
      TEST @Value(_element_index.total_count) > 1
      TEST @Value(_element_index) = @Value(_element_index.min)
      TEST @Value(_element_index) = @Value(_element_index.max)
    TEST_MODE = TEST
    PASSED -> DuplicateFilter
    FAILED -> DuplicateFilter_3
DuplicateFilter
    INPUT_ORDERED_CHOICE = No
    KEYATTR = _pLRS_Route_ID
    UNIQUE -> AttributeKeeper
AttributeKeeper
    CREATE_BULK_MODE_FEATURES = NO
    KEEP_ATTRS = _pLRS_Route_ID
    -> Lollipops (output)
Lollipops (output)
DuplicateFilter_3
    INPUT_ORDERED_CHOICE = No
    KEYATTR = _pLRS_Route_ID
    UNIQUE -> AttributeKeeper_2
AttributeKeeper_2
    CREATE_BULK_MODE_FEATURES = NO
    KEEP_ATTRS = _pLRS_Route_ID
    -> Other (output)
Other (output)

FME custom transformer QC_Summarizer
Generate summary report for use by QCers

Parameters:
- pInputCol =   # "" Select an Attribute Name From QC Input
- _pErrCode = @Value(_oErrCode)   # Error Code Attribute
- pRouteCount =   # Total Route Count

QC_Output (input)
    -> StatisticsCalculator
QC_Input (input)
    -> AttributeCreator_2
Summary_output (output)

Bookmark: Summary
StatisticsCalculator
    CALCULATION_MODE = LEXICAL
    FEAT_STATS = _oErrCode,LEXICAL,,,COUNT,<Unused>,<Unused>,,,,<Unused>,<Unused>,<Unused>,,
    GROUP_BY = _oErrCode
    SUMMARY -> StatisticsCalculator_4
    SUMMARY -> JsonAutoGenerator
JsonAutoGenerator: JSONAutoGenerator
    -> Junction_3
StatisticsCalculator_4
    CALCULATION_MODE = NUMERIC
    FEAT_STATS = _oErrCode.total_count,NUMERIC_MODE,,,,SUM,,,,,,,,,
    SUMMARY -> AttributeRenamer_4
AttributeRenamer_4
    ATTR_TABLE = RENAME_SET_DEFAULT _oErrCode.total_count.sum > _error_count
    MISSING_INPUT_ATTRS = REMOVE
    -> Junction_3
AttributeCreator_2
    ATTR_TABLE = SET_TO _Input_count = $(pRouteCount)
    -> Junction_3
Junction_3
    -> StatisticsCalculator_3
StatisticsCalculator_3
    CALCULATION_MODE = LEXICAL
    FEAT_STATS = _result,LEXICAL,MIN,,,<Unused>,<Unused>,,,,<Unused>,<Unused>,<Unused>,,;_Input_count,LEXICAL,MIN,,,<Unused>,<Unused>,,,,<Unused>,<Unused>,<Unused>,,;_error_count,LEXICAL,MIN,,,<Unused>,<Unused>,,,,<Unused>,<Unused>,<Unused>,,
    SUMMARY -> AttributeCreator
AttributeCreator
    ATTR_TABLE:
      SET_TO _result = FME_CONDITIONAL:DEFAULT_VALUE'{"error_count":0, "input_count":@Value(_Input_count.min), "result": null}'BOOL_OP;OR;COMPOSITE_TEST;1;TEST _result.min ATTRIBUTE_HAS_A_VALUE _FME_BLANK_STRING_'{"error_count":@Value(_error_count.min), "input_count":@Value(_Input_count.min), "result": @Value(_result.min)}'FME_NUM_CONDITIONS2___
      SET_TO _error_count = FME_CONDITIONAL:DEFAULT_VALUE'0'BOOL_OP;OR;COMPOSITE_TEST;1;TEST _error_count.min ATTRIBUTE_HAS_A_VALUE _FME_BLANK_STRING_'@Value(_error_count.min)'FME_NUM_CONDITIONS2___
      SET_TO _Input_count = @Value(_Input_count.min)
    -> BulkAttributeRemover
BulkAttributeRemover
    ATTR_EXP = .min
    -> Summary_output (output)

FME custom transformer LRS_RouteQCer_DIR
Check Route Direction Consistency

Parameters:
- _PLRS_ROUTE_ID = @Value(_pLRS_Route_ID)   # Plrs Route Id

Route_System (input)
    -> LRS_GetRouteMeas_2
LRS_GetRouteMeas_2
    pNodeXY = No
    pPrecision = 5
    -> ARM
ARM: AttributeRemover
    REMOVE_ATTRS = _oBegZ,_oEndZ,_part_number
    -> TST_DIRECTION
TST_DIRECTION: Tester
    BOOL_OP = OR
    TEST_CLAUSE = TEST @Value(_oBegMeas) > @Value(_oEndMeas)
    TEST_MODE = TEST
    PASSED -> ARN
ARN: AttributeRenamer
    ATTR_TABLE:
      RENAME_SET_DEFAULT _oBegMeas > _measure1
      RENAME_SET_DEFAULT _oEndMeas > _measure2
      RENAME_SET_DEFAULT _oBegX > _pt1x
      RENAME_SET_DEFAULT _oBegY > _pt1y
      RENAME_SET_DEFAULT _oEndX > _pt2x
      RENAME_SET_DEFAULT _oEndY > _pt2y
    -> AC_ERRCODE
AC_ERRCODE: AttributeCreator
    ATTR_TABLE = SET_TO _oErrCode = DIR
    -> Output (output)
Output (output)

FME custom transformer LRS_RouteQCer_SPK
Identify Spikes

Parameters:
- _PLRS_ROUTE_ID = @Value(_pLRS_Route_ID)   # Plrs Route Id
- pSpikeAngle = 25   # Maximum Spike Angle

Route_System (input)
    -> SR_45
SR_45: SpikeRemover
    DIMENSIONS = 2D
    ITERATIVE = No
    SPIKEANGLE = $(pSpikeAngle)
    REMOVED -> AC_SPK
AC_SPK: AttributeCreator
    ATTR_TABLE:
      SET_TO _oErrCode = SPK
      SET_TO _length = @double(@Value(_spike_length1) + @Value(_spike_length2))
    -> AK_4
AK_4: AttributeKeeper
    CREATE_BULK_MODE_FEATURES = NO
    KEEP_ATTRS = _pLRS_Route_ID,_length,_oErrCode
    -> CE_NODE_2
CE_NODE_2: CoordinateExtractor
    IND = 0
    MODE = Specify Coordinate
    X_ATTR = _pt1x
    Y_ATTR = _pt1y
    -> Output (output)
Output (output)
