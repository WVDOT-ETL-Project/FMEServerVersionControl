FME workspace Event_Intralayer_TOPO_Batch.fmw

Parameters:
- pEnv = STG   # Select Database Environment
- pLayers = RH.LRSE_FACILITY RH.LRSE_CENSUS_URBAN_CODE
- pRouteIDSignSystem = 1 2 3 4
- pRouteIDPattern = 3%   # Enter Route ID Pattern
- pObserveDate =   # Pick a Date (Blank for today)
- pVersion = SDE.DEFAULT   # SDE Version ("EXECUTIVE\E029937".RCE_233341)
- pPathOutput = \\dotb6gistest1\share\ReportOutput\   # Disk file output path
- FME_SHAREDRESOURCE_TEMP = \\DOTB6GISTEST1\share\GISOutput\FMEServerCache   # FME Server Temporary Resource Directory

Creator
    GEOMTYPE = Geometry Object
    NUM = 1
    CREATED -> WV_Initiator
Note: Make sure the pass the current parameters to the CT!!!
WV_Initiator
    pDOT_RouteScope = 1
    pEnv = $(pEnv)
    pObserveDate = $(pObserveDate)
    pRouteIDPattern = $(pRouteIDPattern)
    pRouteIDSignSystem = $(pRouteIDSignSystem)
    pRouteIDs = 1540002100000
    -> FRD_SDE_STG_RIL_LRS_2 [INITIATOR]
    -> FRD_SDE_STG_RIL_LRS_3 [INITIATOR]
Note: Expand Json summary into tabular form
TabularSummary_2
    _ERROR_COUNT = @Value(_error_count)
    _INPUT_COUNT = @Value(_Input_count)
    _RESULT = @Value(_result)
    -> FWT-Excel_2 [Summary]
    -> InlineQuerier [Output]
InlineQuerier
    QUERY_DEF:
      Merged,SELECT "Input Count","Total Error Count", "Error Code", "Count", "_dataset"
      FROM "Output", "Summary",FIRST
    QUERY_SCHEMA = Merged,"Input Count",text,"Total Error Count",varchar(200),"Error Code",varchar(200),Count,varchar(200),_dataset,text
    TABLE_DEF = Summary,_dataset,text,_total_features_written,varchar(20),Output,"Total Error Count",varchar(200),"Input Count",text,"Error Code",varchar(200),Count,varchar(200)
    Merged -> HTMLReportGenerator

Bookmark: Intralayer Topology QC by Route ID - INTERACTIVE
Note: Event generic, no geometry, with only LRS columns exposed / Notice version setting here!
FRD_SDE_STG_RIL_LRS_2: FeatureReader
    ATTRIBUTES = RH.LRSE_DISTRICT,"OBJECTID,DISTRICT_ID,ROUTE_ID,FROM_MEASURE,TO_MEASURE,DISTRICT,FIELD_ESTABLISH_DATE,SYSTEM_CREATE_DATE,SYSTEM_MOD_DATE,RH_FROM_DATE,RH_TO_DATE,USER_CREATE,USER_MOD,LocError,GDB_GEOMATTR_DATA",RH.LRSE_FEDERAL_AID,"OBJECTID,FEDERAL_AID_ID,ROUTE_ID,FROM_MEASURE,TO_MEASURE,FAS_TYPE,FIELD_ESTABLISH_DATE,SYSTEM_CREATE_DATE,SYSTEM_MOD_DATE,RH_FROM_DATE,RH_TO_DATE,USER_CREATE,USER_MOD,LocError,GDB_GEOMATTR_DATA",RH.LRSE_MAINT_OPERATIONS,"OBJECTID,MAINT_OPERATIONS_ID,ROUTE_ID,FROM_MEASURE,TO_MEASURE,SERVICE_ORG,SECTION_TYPE,IDENT,RTSIGN_NAME,LOCATION,COMMENTS,COMMENTS2,FIELD_ESTABLISH_DATE,SYSTEM_CREATE_DATE,SYSTEM_MOD_DATE,RH_FROM_DATE,RH_TO_DATE,USER_CREATE,USER_MOD,LocError,DISTRICT,Name,GDB_GEOMATTR_DATA",RH.LRSE_NHS,"OBJECTID,NHS_ID,ROUTE_ID,FROM_MEASURE,TO_MEASURE,NHS,NHS_APPROVED_DATE,FIELD_ESTABLISH_DATE,SYSTEM_CREATE_DATE,SYSTEM_MOD_DATE,RH_FROM_DATE,RH_TO_DATE,USER_CREATE,USER_MOD,LocError,GDB_GEOMATTR_DATA",RH.LRSE_STATE_FUNCT_CLASS,"OBJECTID,STATE_FUNCTIONAL_CLASS_ID,ROUTE_ID,FROM_MEASURE,TO_MEASURE,STATE_FUNCTIONAL_CLASS,FIELD_ESTABLISH_DATE,SYSTEM_CREATE_DATE,SYSTEM_MOD_DATE,RH_FROM_DATE,RH_TO_DATE,USER_CREATE,USER_MOD,LocError,GDB_GEOMATTR_DATA",RH.LRSE_SURFACE_TYPE,"OBJECTID,SURFACE_TYPE_ID,ROUTE_ID,FROM_MEASURE,TO_MEASURE,SURFACE_TYPE,FIELD_ESTABLISH_DATE,SYSTEM_CREATE_DATE,SYSTEM_MOD_DATE,RH_FROM_DATE,RH_TO_DATE,USER_CREATE,USER_MOD,LocError,GDB_GEOMATTR_DATA"
    ATTRS_TO_EXPOSE = FROM_MEASURE OBJECTID RH_FROM_DATE RH_TO_DATE ROUTE_ID TO_MEASURE fme_feature_type
    ATTR_ACCUM_MODE = Only Use Result
    COMBINE_GEOM = Use Initiator
    FEATURETYPES = $(pLayers)
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = $(pVersion)
    GEODATABASE_SDE_VERSION_TYPE = Transactional Version
    INTERACT = NONE
    OUTPUT_FEATURES_DISPLAY = Data Features
    WHERE = @Value(_filter_event_by_observe_date_route_id)
    <OTHER> -> LRS_EventQCer_3 [LRS_Events]
Note: Route system with Geometry, Using generic port and expose CO_ROUTEID
FRD_SDE_STG_RIL_LRS_3: FeatureReader
    ATTRIBUTES = RH.LRSN_County_Milepoint,"OBJECTID,FROMDATE,TODATE,CO_CountyID,CO_SignSystem,CO_RouteNumber,CO_SubRoute,CO_SuppCode,CO_RouteDirection,CO_ExitNumber,CO_RampLetter,CO_ROUTEID,SurveyDirection,CO_RouteLabel,SHAPE.STLength()"
    ATTRS_TO_EXPOSE = CO_ROUTEID
    ATTR_ACCUM_MODE = Only Use Result
    COMBINE_GEOM = Use Result
    FEATURETYPES = RH.LRSN_County_Milepoint
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = $(pVersion)
    GEODATABASE_SDE_VERSION_TYPE = Transactional Version
    INTERACT = NONE
    OUTPUT_FEATURES_DISPLAY = Data Features
    WHERE = @Value(_filter_route_by_observe_date_route_id)
    <OTHER> -> LRS_EventQCer_3 [LRS_Route_Features]
LRS_EventQCer_3
    pEventGroup = fme_feature_type
    pEvent_F_Meas = FROM_MEASURE
    pEvent_ID = OBJECTID
    pEvent_Route_ID = ROUTE_ID
    pEvent_T_Meas = TO_MEASURE
    pLRS_Route_ID = CO_ROUTEID
    pMinEventLength = 10
    pPrecision = 3
    pQCRules = EXTENT
    Detail -> AttributeManager_3
    Summary -> TabularSummary_2

Bookmark: Excel output
AttributeManager_3
    USER_EXPOSED_ATTRIBUTES = Error.total_count,EventGroup,Error,_oEventGroup,_oEvent2_ID
    -> FWT-Excel_2 [QC_Report]
Note: report name with time stemp
FWT-Excel_2: FeatureWriter
    DATASET = $(pPathOutput)\$(WORKSPACE_NAME)-@int64(@DateTimeNow()/10000)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
    SUMMARY -> InlineQuerier [Summary]

Bookmark: Serverapp Output
HTMLReportGenerator
    CONTENT_LIST = HEADER TABLE HEADER
    PAGE_CONFIG = HEADER{{TEXT;Batch QC Completed Successfully;HEADER;H1;HEADER_ID;;ALIGNMENT;CENTER;COLOR;0,0,0;FME_CONTROLLER_QUERY_FILE;transformers/dependencies/html5/Header.fme;FME_CONTROLLER_CHOICE;Header}}TABLE{{STYLE;DEFAULT;TABLE;Error Code|Error Code/Count|Total/Total Error Count|Total Error/Input Count|Source Count;FME_CONTROLLER_QUERY_FILE;transformers/dependencies/html5/Table.fme;FME_CONTROLLER_CHOICE;Table}}HEADER{{TEXT;QC Report:  @Value(_dataset).xlsx;HEADER;H5;HEADER_ID;;ALIGNMENT;LEFT;COLOR;0,0,0;FME_CONTROLLER_QUERY_FILE;transformers/dependencies/html5/Header.fme;FME_CONTROLLER_CHOICE;Header}}
    TITLE = RouteBatchQCSummary
    -> FWT-HTML [HTML]
Note: For FME App Display
FWT-HTML: FeatureWriter
    DATASET = $(FME_SHAREDRESOURCE_TEMP)\$(WORKSPACE_NAME)_Summary.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written

FME custom transformer TabularSummary
Expand the summary QC in json to tabular form

Parameters:
- _ERROR_COUNT = @Value(_error_count)   # Error Count
- _INPUT_COUNT = @Value(_Input_count)   # Input Count
- _RESULT = @Value(_result)   # Result

Input (input)
    -> JSONFragmenter
JSONFragmenter
    EXPLODE_FORMAT = JSON
    EXTRACT_ATTR = No
    JSON_ATTR = _result
    JSON_QUERY = json["result"]
    READ_FROM_FILE = NO
    REJECT_EMPTY_LISTS = YES
    FRAGMENTS -> TST-ERR
TST-ERR: Tester
    BOOL_OP = OR
    TEST_CLAUSE = TEST @Value(_error_count) > 0
    TEST_MODE = TEST
    PASSED -> JSONFragmenter_2
    FAILED -> AttributeManager_2
JSONFragmenter_2
    EXPLODE_FORMAT = JSON
    EXTRACT_ATTR = No
    JSON_ATTR = _result
    JSON_QUERY = json[*]
    READ_FROM_FILE = NO
    REJECT_EMPTY_LISTS = YES
    FRAGMENTS -> JSONFlattener
JSONFlattener
    ERROR_LIST_ATTR = _json_error
    JSON_DOCUMENT = @Value(_result)
    READ_FROM_FILE = NO
    RECURSIVE = Yes
    -> AttributeExposer
AttributeExposer
    ATTR_LIST = _oErrCode,_oRouteID.total_count
    -> AttributeManager_3
AttributeManager_3
    ATTR_TABLE:
      REMOVE _result
      RENAME_SET_VALUE _error_count > Total Error Count
      RENAME_SET_VALUE _Input_count > Input Count
      REMOVE json_type
      REMOVE json_index
      RENAME_SET_VALUE _oErrCode > Error Code
      RENAME_SET_VALUE _oRouteID.total_count > Count
    -> Output (output)
AttributeManager_2
    ATTR_TABLE:
      REMOVE _result
      RENAME_SET_VALUE _error_count > Total Error Count
      RENAME_SET_VALUE _Input_count > Input Count
      REMOVE json_type
      REMOVE json_index
    -> Output (output)
Output (output)
