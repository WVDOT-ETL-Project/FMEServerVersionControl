FME workspace Event_Interlayer_Extent_Batch.fmw
Title: WV_ETL_General

Parameters:
- pEnv = STG   # Select Database Environment
- pLayers = RH.LRSE_CENSUS_URBAN_CODE RH.LRSE_FACILITY RH.LRSE_FEDERAL_AID RH.LRSE_NAT_FUNCT_CLASS RH.LRSE_NHS RH.LRSE_OWNERSHIP RH.LRSE_STATE_FUNCT_CLASS RH.LRSE_SURFACE_TYPE RH.LRSE_URBAN_CODE RH.LRSE_COUNTY RH.LRSE_DISTRICT RH.LRSE_FOREST_ROUTE RH.LRSE_GRADE_WIDTH RH.LRSE_MAINT_OPERATIONS RH.LRSE_MEDIAN RH.LRSE_PAVEMENT_WIDTH RH.LRSE_FAULTING RH.LRSE_IRI RH.LRSE_RUTTING RH.LRSE_AADT RH.LRSE_ACCESS_CONTROL RH.LRSE_AVG_LANE_WIDTH RH.LRSE_DES_TRUCK_ROUTE RH.LRSE_ORIG_SURVEY_DIR RH.LRSE_PEAK_LANES RH.LRSE_REVERSE_LANE RH.LRSE_RURAL_MUNI RH.LRSE_RURAL_URBAN RH.LRSE_SPECIAL_SYSTEM RH.LRSE_STRAHNET RH.LRSE_THROUGH_LANES RH.LRSE_YEAR_LAST_IMPROV
- pDOT_RouteScope = 1   # Routes Scope for QC
- pGroupPattern =   # By Route Pattern and Category
- pRouteIDSignSystem = 1 2 3 4 5 6 7 8
- pRouteIDPattern = 3%   # Enter Route ID Pattern
- pObserveDate =   # Pick a Date (Blank for today)
- pVersion = SDE.DEFAULT   # SDE Version ("EXECUTIVE\E029937".RCE_233341)
- pPathOutput = \\dotb6gistest1\share\ReportOutput\   # Disk file output path
- FME_SHAREDRESOURCE_TEMP = \\dotb6gistest1\share\GISOutput\FMEServerCache   # FME Server Temporary Resource Directory

Creator
    GEOMTYPE = Geometry Object
    NUM = 1
    CREATED -> WV_Initiator
WV_Initiator
    pDOT_RouteScope = 1
    pEnv = STG
    pRouteIDPattern = %
    -> FRD_SQL_RIL_LRS_STG_2 [INITIATOR]
FRD_SQL_RIL_LRS_STG_2: FeatureReader
    ATTRIBUTES = RH.LRSE_DISTRICT,"OBJECTID,DISTRICT_ID,ROUTE_ID,FROM_MEASURE,TO_MEASURE,DISTRICT,FIELD_ESTABLISH_DATE,SYSTEM_CREATE_DATE,SYSTEM_MOD_DATE,RH_FROM_DATE,RH_TO_DATE,USER_CREATE,USER_MOD,LocError,GDB_GEOMATTR_DATA",RH.LRSE_FEDERAL_AID,"OBJECTID,FEDERAL_AID_ID,ROUTE_ID,FROM_MEASURE,TO_MEASURE,FAS_TYPE,FIELD_ESTABLISH_DATE,SYSTEM_CREATE_DATE,SYSTEM_MOD_DATE,RH_FROM_DATE,RH_TO_DATE,USER_CREATE,USER_MOD,LocError,GDB_GEOMATTR_DATA",RH.LRSE_MAINT_OPERATIONS,"OBJECTID,MAINT_OPERATIONS_ID,ROUTE_ID,FROM_MEASURE,TO_MEASURE,SERVICE_ORG,SECTION_TYPE,IDENT,RTSIGN_NAME,LOCATION,COMMENTS,COMMENTS2,FIELD_ESTABLISH_DATE,SYSTEM_CREATE_DATE,SYSTEM_MOD_DATE,RH_FROM_DATE,RH_TO_DATE,USER_CREATE,USER_MOD,LocError,DISTRICT,Name,GDB_GEOMATTR_DATA",RH.LRSE_NHS,"OBJECTID,NHS_ID,ROUTE_ID,FROM_MEASURE,TO_MEASURE,NHS,NHS_APPROVED_DATE,FIELD_ESTABLISH_DATE,SYSTEM_CREATE_DATE,SYSTEM_MOD_DATE,RH_FROM_DATE,RH_TO_DATE,USER_CREATE,USER_MOD,LocError,GDB_GEOMATTR_DATA",RH.LRSE_STATE_FUNCT_CLASS,"OBJECTID,STATE_FUNCTIONAL_CLASS_ID,ROUTE_ID,FROM_MEASURE,TO_MEASURE,STATE_FUNCTIONAL_CLASS,FIELD_ESTABLISH_DATE,SYSTEM_CREATE_DATE,SYSTEM_MOD_DATE,RH_FROM_DATE,RH_TO_DATE,USER_CREATE,USER_MOD,LocError,GDB_GEOMATTR_DATA",RH.LRSE_SURFACE_TYPE,"OBJECTID,SURFACE_TYPE_ID,ROUTE_ID,FROM_MEASURE,TO_MEASURE,SURFACE_TYPE,FIELD_ESTABLISH_DATE,SYSTEM_CREATE_DATE,SYSTEM_MOD_DATE,RH_FROM_DATE,RH_TO_DATE,USER_CREATE,USER_MOD,LocError,GDB_GEOMATTR_DATA"
    ATTRS_TO_EXPOSE = FROM_MEASURE OBJECTID RH_FROM_DATE RH_TO_DATE ROUTE_ID TO_MEASURE fme_feature_type
    ATTR_ACCUM_MODE = Only Use Result
    COMBINE_GEOM = Use Initiator
    FEATURETYPES = $(pLayers)
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = @Value(_connSDE_RIL_LRS)
    GEODATABASE_SDE_CREATE_FEATURE_TABLES_FROM_DATA = Yes
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEODATABASE_SDE_VERSION = $(pVersion)
    GEODATABASE_SDE_VERSION_TYPE = Transactional Version
    INTERACT = NONE
    OUTPUT_FEATURES_DISPLAY = Data Features
    WHERE = @Value(_filter_event_by_observe_date_route_pattern)
    <OTHER> -> DuplicateFilter_3
DuplicateFilter_3
    INPUT_ORDERED_CHOICE = No
    KEYATTR = fme_feature_type
    UNIQUE -> StatisticsCalculator_5
    UNIQUE -> lrs_event_overlayer_2
    DUPLICATE -> lrs_event_overlayer_2
lrs_event_overlayer_2
    FME_FEATURE_TYPE = @Value(fme_feature_type)
    FROM_MEASURE = @Value(FROM_MEASURE)
    OBJECTID = @Value(OBJECTID)
    ROUTE_ID = @Value(ROUTE_ID)
    TO_MEASURE = @Value(TO_MEASURE)
    pLayers = $(pLayers)
    GapReport -> PythonCaller
    -> StatisticsCalculator

Bookmark: Ensure more than one layer to process
StatisticsCalculator_5
    CALCULATION_MODE = NUMERIC
    FEAT_STATS = fme_feature_type,NUMERIC_MODE,,,COUNT,,,,,,,,,,
    SUMMARY -> Tester_3
Note: More then one layer
Tester_3
    BOOL_OP = OR
    TEST_CLAUSE = TEST @Value(fme_feature_type.total_count) > 1
    TEST_MODE = TEST
    FAILED -> Terminator
Terminator
    MESSAGE = Translation Terminated

Bookmark: Batch Report output
Note: Expose attributes by parameter
PythonCaller
    NEW_ATTRIBUTES = $(pLayers)
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> AttributeCreator
AttributeCreator
    ATTR_TABLE = SET_TO ROUTE_ID = '@Value(ROUTE_ID)
    -> FWT-Excel [Output]
Note: Gap report to excel
FWT-Excel: FeatureWriter
    DATASET = $(pPathOutput)\$(WORKSPACE_NAME)-@int64(@DateTimeNow()/10000)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
    SUMMARY -> InlineQuerier [Summary]

Bookmark: Summary
StatisticsCalculator
    CALCULATION_MODE = NUMERIC
    FEAT_STATS = OBJECTID,NUMERIC_MODE,,,COUNT,,,,,,,,,,
    GROUP_BY = fme_feature_type
    SUMMARY -> AttributeManager
AttributeManager
    ATTR_TABLE:
      RENAME_SET_VALUE fme_feature_type > Layer_Name
      RENAME_SET_VALUE OBJECTID.total_count > Segment_Count
    -> FWT-Excel [Output00]
    -> InlineQuerier [Output]

Bookmark: For FME Server App
InlineQuerier
    QUERY_DEF:
      Merged,SELECT "Layer_Name","Segment_Count","_dataset"
      FROM "Output", "Summary",FIRST
    QUERY_SCHEMA = Merged,Layer_Name,varchar(200),Segment_Count,varchar(20),_dataset,text
    TABLE_DEF = Summary,_dataset,text,_total_features_written,varchar(20),Output,Layer_Name,varchar(200),Segment_Count,varchar(20)
    Merged -> HTMLReportGenerator
HTMLReportGenerator
    CONTENT_LIST = HEADER TABLE HEADER
    PAGE_CONFIG = HEADER{{TEXT;Batch QC Completed Successfully;HEADER;H1;HEADER_ID;;ALIGNMENT;CENTER;COLOR;0,0,0;FME_CONTROLLER_QUERY_FILE;transformers/dependencies/html5/Header.fme;FME_CONTROLLER_CHOICE;Header}}TABLE{{STYLE;DEFAULT;TABLE;Layer_Name|Layer Name/Segment_Count|Segment Count;FME_CONTROLLER_QUERY_FILE;transformers/dependencies/html5/Table.fme;FME_CONTROLLER_CHOICE;Table}}HEADER{{TEXT;QC Report: @Value(_dataset).xlsx;HEADER;H5;HEADER_ID;;ALIGNMENT;LEFT;COLOR;0,0,0;FME_CONTROLLER_QUERY_FILE;transformers/dependencies/html5/Header.fme;FME_CONTROLLER_CHOICE;Header}}
    TITLE = RouteBatchQCSummary
    -> FWT-HTML [HTML]
Note: For FME App Display
FWT-HTML: FeatureWriter
    DATASET = $(FME_SHAREDRESOURCE_TEMP)\$(WORKSPACE_NAME)_Summary.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written

FME custom transformer lrs_event_overlayer
Takes a single stream event and conducts event overlay with raw data and gap report

Parameters:
- pLayers =
- FROM_MEASURE = @Value(FROM_MEASURE)   # From Measure
- ROUTE_ID = @Value(ROUTE_ID)   # Route Id
- TO_MEASURE = @Value(TO_MEASURE)   # To Measure
- FME_FEATURE_TYPE = @Value(fme_feature_type)   # Fme Feature Type
- OBJECTID = @Value(OBJECTID)

Input (input)
    -> Counter
Note: Add counter to join later
Counter
    CNT_ATTR = _id
    DOMAIN = counter
    SCOPE = Global
    START = 0
    -> InlineQuerier [Input_2]
Note: Add layer count
InlineQuerier
    QUERY_DEF:
      Ouput,WITH foo AS (SELECT DISTINCT "fme_feature_type" FROM "Input_2")
      , foo2 AS (SELECT COUNT(1) "_layer_count" FROM foo)
      SELECT "_id","fme_feature_type","FROM_MEASURE","OBJECTID","ROUTE_ID","TO_MEASURE", "_layer_count"
      FROM "Input_2", foo2
      ,FIRST
    QUERY_SCHEMA = Ouput,_id,integer,fme_feature_type,varchar(200),FROM_MEASURE,varchar(200),OBJECTID,varchar(200),ROUTE_ID,varchar(200),TO_MEASURE,varchar(200),_layer_count,
    TABLE_DEF = Input_2,FROM_MEASURE,varchar(200),ROUTE_ID,varchar(200),TO_MEASURE,varchar(200),fme_feature_type,varchar(200),OBJECTID,varchar(200),_id,integer
    Ouput -> LRS_EventLineOnLine_SS [LRS_Events]
    Ouput -> FeatureJoiner [RIGHT]
LRS_EventLineOnLine_SS
    pEvent_F_Meas = FROM_MEASURE
    pEvent_ID = _id
    pEvent_Route_ID = ROUTE_ID
    pEvent_T_Meas = TO_MEASURE
    pLayer_Name = fme_feature_type
    pPrecision = 3
    -> ListExploder
ListExploder
    ATTR_ACCUM_MODE = Merge List Attributes
    ATTR_CONFLICT_RES = Use List Attribute Values
    INDEX_ATTR = _element_index
    LIST_ATTR = _oEventIds{}
    ELEMENTS -> FeatureJoiner [LEFT]
FeatureJoiner
    ATTR_CONFLICT_RES = Prefer Left
    GEOMETRY_HANDLING = Prefer Left
    JOIN_KEYS = _pEvent_ID _id AUTO
    JOIN_MODE = Inner
    JOINED -> StatisticsCalculator_3
StatisticsCalculator_3
    CALCULATION_MODE = NUMERIC
    FEAT_STATS = _id,NUMERIC_MODE,,,COUNT,,,,,,,,,,
    GROUP_BY = _oFMeas _oTMeas _pEvent_Route_ID
    COMPLETE -> Tester_2
Note: gap occurs when layer counter is larger than count
Tester_2
    BOOL_OP = OR
    TEST_CLAUSE = TEST @Value(_id.total_count) < @Value(_layer_count)
    TEST_MODE = TEST
    PASSED -> AttributePivoter
    PASSED -> AttributeManager
    FAILED -> AttributeManager
AttributePivoter
    COLUMN_GROUP_ATTR = fme_feature_type
    GROUP_TOTALS_TAG = Total
    INCLUDE_GRAND_TOTALS = No
    PIVOT_ATTR = OBJECTID
    PIVOT_SUMMARY_TYPES = Min
    ROW_GROUP_ATTRS = _oFMeas _oTMeas _pEvent_Route_ID
    DATA -> AttributeRemover
AttributeRemover
    REMOVE_ATTRS = FROM_MEASURE,TO_MEASURE,_element_index,OBJECTID,ROUTE_ID,fme_feature_type,_pEvent_ID,_layer_count,_id,_id.total_count
    -> AttributeManager_2
AttributeManager_2
    ATTR_TABLE:
      RENAME_SET_VALUE _pEvent_Route_ID > ROUTE_ID
      RENAME_SET_VALUE _oFMeas > FROM_MEASURE
      RENAME_SET_VALUE _oTMeas > TO_MEASURE
    -> GapReport (output)
GapReport (output)
AttributeManager
    ATTR_TABLE:
      REMOVE _element_index
      REMOVE _id
      REMOVE _id.total_count
    USER_EXPOSED_ATTRIBUTES = _count,_count.total_count
    -> Output (output)
Output (output)
