FME workspace Lab3.fmw

Parameters:
- CONNECTION = fme@STG_SQL_RIL_LRS_STG   # SQL DB Connection
- LAYER = RH.LRSE_COUNTY   # SQL DB Layer

Starter
    -> FeatureReader [INITIATOR]
    -> FeatureReader_Param [INITIATOR]
FeatureReader
    ATTRIBUTES = RH.LRSE_COUNTY,"OBJECTID,COUNTY_ID,ROUTE_ID,FROM_MEASURE,TO_MEASURE,COUNTY,FIELD_ESTABLISH_DATE,SYSTEM_CREATE_DATE,SYSTEM_MOD_DATE,RH_FROM_DATE,RH_TO_DATE,USER_CREATE,USER_MOD,LocError,GDB_GEOMATTR_DATA"
    ATTR_ACCUM_MODE = Only Use Result
    COMBINE_GEOM = Use Result
    DATASET = fme@STG_SQL_RIL_LRS_STG
    FEATURETYPES = RH.LRSE_COUNTY
    FORMAT = MSSQL_SPATIAL
    INTERACT = NONE
    MAX_FEATURES = 20
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = fme@STG_SQL_RIL_LRS_STG
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    RH.LRSE_COUNTY -> FeatureWriter [RH.LRSE_COUNTY]
FeatureWriter
    DATASET = \\DOTB6GISTEST1\share\FME\Workspaces\Training\ServerOutput
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
FeatureReader_Param
    ATTRIBUTES = RH.LRSE_COUNTY,"OBJECTID,COUNTY_ID,ROUTE_ID,FROM_MEASURE,TO_MEASURE,COUNTY,FIELD_ESTABLISH_DATE,SYSTEM_CREATE_DATE,SYSTEM_MOD_DATE,RH_FROM_DATE,RH_TO_DATE,USER_CREATE,USER_MOD,LocError,GDB_GEOMATTR_DATA"
    ATTR_ACCUM_MODE = Only Use Result
    COMBINE_GEOM = Use Result
    DATASET = $(CONNECTION)
    FEATURETYPES = $(LAYER)
    FORMAT = MSSQL_SPATIAL
    INTERACT = NONE
    MAX_FEATURES = 20
    MSSQL_SPATIAL_APPLICATION_INTENT = ReadWrite
    MSSQL_SPATIAL_COMMAND_TIMEOUT = 30
    MSSQL_SPATIAL_CREATE_FEATURE_TABLES_FROM_DATA = Yes
    MSSQL_SPATIAL_HANDLE_MULTIPLE_SPATIAL_COLUMNS = NO
    MSSQL_SPATIAL_NAMED_CONNECTION = $(CONNECTION)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_USE_MAKE_VALID = NO
    MSSQL_SPATIAL_USE_SEARCH_ENVELOPE = NO
    OUTPUT_FEATURES_DISPLAY = Schema and Data Features
    <OTHER> -> FeatureWriter_Param [RH.LRSE_COUNTY]
FeatureWriter_Param
    DATASET = \\DOTB6GISTEST1\share\FME\Workspaces\Training\ServerOutput
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written

FME custom transformer Starter
This transformer is intended to start a workspace branch without the use of the creator transformer. This will end up without additional attributes (_creation_instance) at the end of the workspace.

Creator
    GEOMTYPE = Geometry Object
    NUM = 1
    CREATED -> Output (output)
Output (output)
